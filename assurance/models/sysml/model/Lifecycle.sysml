// GENERATED by assurance/models/sysml/tools/gen_behaviour.py from the documents of record. Do not edit;
// change the record and regenerate (README §7).

package LionDriverLifecycle {
    doc /* The life of an installed item (WP-S-06 §3): its phases in order, and in each phase the production and
           operation requirements TSR-8nn its procedures must meet. WP-S-06 stays the source; check B1 holds this
           file to it and B4 to the requirements of the model. */

    private import LionDriverLibrary::*;

    action def InstalledItemLifecycle {
        doc /* Life of an installed item, from installation to decommissioning (WP-S-06 §3) */
        action installationAndProvisioning : LifecyclePhase {
            doc /* Installation and provisioning ("production") */
            :>> section = "3.1";
            action tsr_801 : ProcedureStep {
                doc /* Only a released LionDriver baseline shall be installed: the installed openpilot commit, AGNOS version and model artefact hashes shall equal the release record, and the build shall not be dirty. */
                :>> tsr = "TSR-801";
                :>> asil = "B‡";
                :>> parent = "SG-01…07; T-03";
                :>> steps = "INS-15, INS-16, INS-18; SPC-04";
                :>> record = "R-SW record, second-person check";
                :>> status = "waiting";
                :>> statusNote = "release channel not yet defined";
            }
            action tsr_802 : ProcedureStep {
                doc /* The panda firmware shall be the release-signed, non-debug build recorded in the release record; its version string and signature shall be compared before first engagement. */
                :>> tsr = "TSR-802";
                :>> asil = "B‡";
                :>> parent = "FSR-01.10; TSR-511, 514";
                :>> steps = "INS-17; SPC-05";
                :>> record = "R-SW";
                :>> status = "blocked";
                :>> statusNote = "Blocked in substance by GAP-24/25";
            }
            action tsr_803 : ProcedureStep {
                doc /* Every vehicle ECU firmware version (engine, EPS, ABS, radar, camera) shall equal the reference record before engagement; a mismatch shall put the item in dashcam mode until an impact analysis extends the scope. */
                :>> tsr = "TSR-803";
                :>> asil = "B‡";
                :>> parent = "AOU-01…05; WP-M-12";
                :>> steps = "INS-21; SPC-07; WP-O-01 §6";
                :>> record = "R-CFG raw FW query output";
                :>> status = "defined";
                :>> statusNote = "Procedure defined";
            }
            action tsr_804 : ProcedureStep {
                doc /* The installed configuration shall show fingerprint TOYOTA_COROLLA_TSS2 (exact, not fuzzy), safety model toyota, safety parameter 73, alternative experience 0, openpilot longitudinal on, both in carParams and in pandaStates. */
                :>> tsr = "TSR-804";
                :>> asil = "B‡";
                :>> parent = "FSR-01.10; TSR-512";
                :>> steps = "INS-22, INS-23, INS-24; SPC-06";
                :>> record = "R-CFG";
                :>> status = "defined";
                :>> statusNote = "so the check confirms it";
            }
            action tsr_805 : ProcedureStep {
                doc /* Harness seating and the relay intercept/PCS-forwarding function shall be verified at installation: no relay malfunction or CAN errors, intercepted messages absent on the car side, PCS-relevant camera messages present on the car side with LD-SDA disengaged. */
                :>> tsr = "TSR-805";
                :>> asil = "B";
                :>> parent = "FSR-07.01, 07.03; TSR-704, 706";
                :>> steps = "INS-11, INS-13, INS-14, INS-27; SPC-01, SPC-02";
                :>> record = "R-INS, R-FUN";
                :>> status = "waiting";
                :>> statusNote = "message list pending";
            }
            action tsr_806 : ProcedureStep {
                doc /* The parameter set shall equal the release record: Experimental Mode per D-08, DisengageOnAccelerator per WP-C-08, debug/maneuver/joystick modes absent, DM demo mode off, SSH off. */
                :>> tsr = "TSR-806";
                :>> asil = "QM (B-sup)";
                :>> parent = "FSR-02.08; TSR-610, 613";
                :>> steps = "INS-19; SPC-09";
                :>> record = "R-SW parameter dump";
                :>> status = "design";
                :>> statusNote = "absent by construction in the reference build";
            }
            action tsr_807 : ProcedureStep {
                doc /* The device shall be mounted within the position tolerance and calibrated within the angle tolerance band derived from the model validation range. */
                :>> tsr = "TSR-807";
                :>> asil = "QM (SOTIF)";
                :>> parent = "AOU-08";
                :>> steps = "INS-09, INS-10, INS-25, INS-26; SPC-03";
                :>> record = "R-CAL";
                :>> status = "waiting";
                :>> statusNote = "Tolerance band TBD";
            }
            action tsr_815 : ProcedureStep {
                doc /* Only devices and harnesses of the approved hardware revision, with clean history, shall be installed; units returned after a field event or decommissioned from another vehicle shall pass refurbishment inspection first. */
                :>> tsr = "TSR-815";
                :>> asil = "B‡";
                :>> parent = "T-04; WP-H-07";
                :>> steps = "INS-01…INS-04; ITS-03…ITS-05";
                :>> record = "R-DEV";
                :>> status = "waiting";
                :>> statusNote = "approved revision TBD";
            }
            action tsr_816 : ProcedureStep {
                doc /* Installation shall be done by a trained installer, and the installation record (R-DEV…R-USR) shall be complete and second-person checked before the first engagement and retained per WP-P-04. */
                :>> tsr = "TSR-816";
                :>> asil = "B‡";
                :>> parent = "ISO 26262-7 §5 (by ref.)";
                :>> steps = "WP-O-01 §5; WP-M-04";
                :>> record = "Record review";
                :>> status = "waiting";
                :>> statusNote = "Template pending";
            }
        }
        action operation : LifecyclePhase {
            doc /* Operation */
            :>> section = "3.2";
            action tsr_811 : ProcedureStep {
                doc /* Before every drive the driver shall perform the pre-drive checks and shall not engage if a check fails (vehicle warning lamps, VSC on, clean camera area, device seated, DM camera unobstructed, no offroad alert, driver fit). */
                :>> tsr = "TSR-811";
                :>> asil = "QM (B-sup)";
                :>> parent = "AOU-06, 08, 09, 10";
                :>> steps = "OPS-01…OPS-07; WP-O-03 §5";
                :>> record = "Briefing acknowledgement";
                :>> status = "design";
                :>> statusNote = "the item itself reads the EPS and ABS/VSC fault codes at start-up";
            }
            action tsr_812 : ProcedureStep {
                doc /* Each driver shall receive the user information and safety warnings before first use and acknowledge them; in the development phase only approved safety drivers shall operate the item. */
                :>> tsr = "TSR-812";
                :>> asil = "QM (B-sup)";
                :>> parent = "AOU-06, AOU-07";
                :>> steps = "WP-O-03 Part A/B; INS-30";
                :>> record = "R-USR";
                :>> status = "defined";
                :>> statusNote = "Defined";
            }
            action tsr_813 : ProcedureStep {
                doc /* Field monitoring shall collect and analyse drive logs and driver reports of every installed item, including every disengagement caused by a safety mechanism (controlsMismatch, relayMalfunction, RX invalid, heartbeat lost, safetyTxBlocked > 0), and feed problem resolution and the safety case. */
                :>> tsr = "TSR-813";
                :>> asil = "QM";
                :>> parent = "SG-01…07; ISO 21448 §13";
                :>> steps = "OPS-11, OPS-12; WP-O-04; WP-P-03";
                :>> record = "Monitoring reports";
                :>> status = "waiting";
                :>> statusNote = "WP-O-04 pending";
            }
        }
        action service : LifecyclePhase {
            doc /* Service (maintenance and repair) */
            :>> section = "3.3";
            action tsr_808 : ProcedureStep {
                doc /* Vehicle service actions that can invalidate an AoU or the calibration (alignment/steering/suspension, EPS or ECM/ABS replacement or reflash, windscreen, camera or radar work, tyre size, brake repair, collision repair, battery disconnection, scan-tool sessions, aftermarket accessories) shall trigger the re-verification defined for that action before the item is engaged again. */
                :>> tsr = "TSR-808";
                :>> asil = "B‡";
                :>> parent = "AOU-01…05, 08, 09";
                :>> steps = "SVC-01…SVC-11";
                :>> record = "R-CAL / R-CFG / R-FUN as listed";
                :>> status = "waiting";
                :>> statusNote = "Toyota service information pending";
            }
            action tsr_809 : ProcedureStep {
                doc /* The reference-configuration check (INS-21…INS-23), PCS-preservation check (INS-27) and harness inspection shall be repeated at least every 6 months and after any service trigger; harness and camera windows inspected monthly. */
                :>> tsr = "TSR-809";
                :>> asil = "B";
                :>> parent = "SG-07; AOU-09; latent faults of TSR-506";
                :>> steps = "PM-01…PM-04";
                :>> record = "Maintenance log";
                :>> status = "defined";
                :>> statusNote = "The 6-month interval is also the latent-fault interval";
            }
            action tsr_817 : ProcedureStep {
                doc /* Item faults shall be handled by replacement, not repair: defective devices or harnesses shall be quarantined, reported and returned; after replacement the full provisioning and configuration steps shall be repeated. */
                :>> tsr = "TSR-817";
                :>> asil = "B‡";
                :>> parent = "T-04";
                :>> steps = "ITS-01…ITS-05";
                :>> record = "Problem report (WP-P-03)";
                :>> status = "defined";
                :>> statusNote = "Defined";
            }
        }
        action softwareUpdates : LifecyclePhase {
            doc /* Software updates */
            :>> section = "3.4";
            action tsr_810 : ProcedureStep {
                doc /* Only released baselines shall be installed by update; until signed updates exist, automatic updates shall be disabled and updates installed manually, followed by INS-15…INS-23; model-weight changes require SOTIF re-evaluation; envelope changes require the envelope verification evidence; parameters shall be re-checked after each update; a withdrawn release shall be replaced or the item put in dashcam mode. */
                :>> tsr = "TSR-810";
                :>> asil = "B‡";
                :>> parent = "FSR-01.10; D-02, D-05; GAP-26";
                :>> steps = "UPD-01…UPD-08; WP-O-05";
                :>> record = "Release record (WP-K-06)";
                :>> status = "defined";
                :>> statusNote = "Defined";
            }
        }
        action decommissioningAndEndOfSupport : LifecyclePhase {
            doc /* Decommissioning and end of support */
            :>> section = "3.5";
            action tsr_814 : ProcedureStep {
                doc /* On removal of the item the stock camera connection shall be restored and stock TSS functions (LTA/LDA, DRCC, PCS) and the absence of DTCs verified; logs needed for field monitoring retrieved; device data, credentials and identity keys wiped or the device kept under LionDriver control with its history recorded. */
                :>> tsr = "TSR-814";
                :>> asil = "B (stock path); CS (data)";
                :>> parent = "SG-07; ISO/SAE 21434 §14 (by ref.)";
                :>> steps = "DEC-01…DEC-11";
                :>> record = "Decommissioning record";
                :>> status = "waiting";
                :>> statusNote = "key-wipe tool pending";
            }
            action tsr_818 : ProcedureStep {
                doc /* At end of support of a release, every user shall be informed with the date after which the release must not be engaged. */
                :>> tsr = "TSR-818";
                :>> asil = "QM";
                :>> parent = "ISO/SAE 21434 §14 (by ref.)";
                :>> steps = "WP-O-02 §7.3; WP-O-05";
                :>> record = "Notification record";
                :>> status = "defined";
                :>> statusNote = "Defined";
            }
        }
        first start then installationAndProvisioning;
        first installationAndProvisioning then operation;
        first operation then service;
        first service then operation;
        first operation then softwareUpdates;
        first softwareUpdates then operation;
        first operation then decommissioningAndEndOfSupport;
        first decommissioningAndEndOfSupport then done;
    }
}
