// GENERATED by assurance/models/sysml/tools/gen_behaviour.py from the documents of record. Do not edit;
// change the record and regenerate (README §7).

package LionDriverStateRecords {
    doc /* The state-machine records of WP-W-05 §5 (assurance/05-software/state-machines), one state def each.
           The records stay the source; check B1 holds this file to them. */

    private import ScalarValues::*;

    metadata def StateRecord {
        attribute file : String;
        attribute units : String[1..*];
    }
    metadata def RecordTransition {
        attribute id : String;
        attribute trigger : String;
        attribute condition : String;
        attribute effect : String;
        attribute build : String;
        attribute swsr : String[0..*];
        attribute gap : String;
        attribute code : String;
    }

    state def <'SM-SAFETY-MODE'> PandaSafetyMode {
        doc /* Panda safety mode */
        @StateRecord { file = "05-software/state-machines/sm-safety-mode.yaml"; units = ("U-PND-MAIN", "U-PND-COMMS"); }
        entry; then SILENT;
        state SILENT;
        state NOOUTPUT;
        state ELM327;
        state TOYOTA;
        state OTHER_CAR;
        transition m1_silent_silent first SILENT then SILENT {
            doc /* M1: reset */
            @RecordTransition { id = "M1"; trigger = "reset"; condition = ""; effect = "set_safety_mode(SILENT)"; build = "all"; swsr = ("SWSR-311", "SWSR-502c"); gap = ""; code = "panda main.c:339"; }
        }
        transition m1_nooutput_silent first NOOUTPUT then SILENT {
            doc /* M1: reset */
            @RecordTransition { id = "M1"; trigger = "reset"; condition = ""; effect = "set_safety_mode(SILENT)"; build = "all"; swsr = ("SWSR-311", "SWSR-502c"); gap = ""; code = "panda main.c:339"; }
        }
        transition m1_elm327_silent first ELM327 then SILENT {
            doc /* M1: reset */
            @RecordTransition { id = "M1"; trigger = "reset"; condition = ""; effect = "set_safety_mode(SILENT)"; build = "all"; swsr = ("SWSR-311", "SWSR-502c"); gap = ""; code = "panda main.c:339"; }
        }
        transition m1_toyota_silent first TOYOTA then SILENT {
            doc /* M1: reset */
            @RecordTransition { id = "M1"; trigger = "reset"; condition = ""; effect = "set_safety_mode(SILENT)"; build = "all"; swsr = ("SWSR-311", "SWSR-502c"); gap = ""; code = "panda main.c:339"; }
        }
        transition m1_other_car_silent first OTHER_CAR then SILENT {
            doc /* M1: reset */
            @RecordTransition { id = "M1"; trigger = "reset"; condition = ""; effect = "set_safety_mode(SILENT)"; build = "all"; swsr = ("SWSR-311", "SWSR-502c"); gap = ""; code = "panda main.c:339"; }
        }
        transition m2_silent_silent first SILENT then SILENT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_silent_nooutput first SILENT then NOOUTPUT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_silent_elm327 first SILENT then ELM327 {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_silent_toyota first SILENT then TOYOTA {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_silent_other_car first SILENT then OTHER_CAR {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_nooutput_silent first NOOUTPUT then SILENT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_nooutput_nooutput first NOOUTPUT then NOOUTPUT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_nooutput_elm327 first NOOUTPUT then ELM327 {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_nooutput_toyota first NOOUTPUT then TOYOTA {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_nooutput_other_car first NOOUTPUT then OTHER_CAR {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_elm327_silent first ELM327 then SILENT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_elm327_nooutput first ELM327 then NOOUTPUT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_elm327_elm327 first ELM327 then ELM327 {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_elm327_toyota first ELM327 then TOYOTA {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_elm327_other_car first ELM327 then OTHER_CAR {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_toyota_silent first TOYOTA then SILENT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_toyota_nooutput first TOYOTA then NOOUTPUT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_toyota_elm327 first TOYOTA then ELM327 {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_toyota_toyota first TOYOTA then TOYOTA {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_toyota_other_car first TOYOTA then OTHER_CAR {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_other_car_silent first OTHER_CAR then SILENT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_other_car_nooutput first OTHER_CAR then NOOUTPUT {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_other_car_elm327 first OTHER_CAR then ELM327 {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_other_car_toyota first OTHER_CAR then TOYOTA {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m2_other_car_other_car first OTHER_CAR then OTHER_CAR {
            doc /* M2: 0xdc (m, p) */
            @RecordTransition { id = "M2"; trigger = "0xdc (m, p)"; condition = "m in the registry"; effect = "reset state; relay per m; CAN re-init"; build = "upstream"; swsr = ("SWSR-311"); gap = ""; code = "panda main_comms.h:243-245; main.c:38-90"; }
        }
        transition m3_silent_silent first SILENT then SILENT {
            doc /* M3: 0xdc (m, p) */
            @RecordTransition { id = "M3"; trigger = "0xdc (m, p)"; condition = "m unknown (set_safety_hooks fails); in the reference build an unknown m is refused by M6 first"; effect = "fall back"; build = "upstream"; swsr = ("SWSR-311"); gap = ""; code = "panda main.c:46-53"; }
        }
        transition m3_nooutput_silent first NOOUTPUT then SILENT {
            doc /* M3: 0xdc (m, p) */
            @RecordTransition { id = "M3"; trigger = "0xdc (m, p)"; condition = "m unknown (set_safety_hooks fails); in the reference build an unknown m is refused by M6 first"; effect = "fall back"; build = "upstream"; swsr = ("SWSR-311"); gap = ""; code = "panda main.c:46-53"; }
        }
        transition m3_elm327_silent first ELM327 then SILENT {
            doc /* M3: 0xdc (m, p) */
            @RecordTransition { id = "M3"; trigger = "0xdc (m, p)"; condition = "m unknown (set_safety_hooks fails); in the reference build an unknown m is refused by M6 first"; effect = "fall back"; build = "upstream"; swsr = ("SWSR-311"); gap = ""; code = "panda main.c:46-53"; }
        }
        transition m3_toyota_silent first TOYOTA then SILENT {
            doc /* M3: 0xdc (m, p) */
            @RecordTransition { id = "M3"; trigger = "0xdc (m, p)"; condition = "m unknown (set_safety_hooks fails); in the reference build an unknown m is refused by M6 first"; effect = "fall back"; build = "upstream"; swsr = ("SWSR-311"); gap = ""; code = "panda main.c:46-53"; }
        }
        transition m3_other_car_silent first OTHER_CAR then SILENT {
            doc /* M3: 0xdc (m, p) */
            @RecordTransition { id = "M3"; trigger = "0xdc (m, p)"; condition = "m unknown (set_safety_hooks fails); in the reference build an unknown m is refused by M6 first"; effect = "fall back"; build = "upstream"; swsr = ("SWSR-311"); gap = ""; code = "panda main.c:46-53"; }
        }
        transition m4_silent_silent first SILENT then SILENT {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_silent_nooutput first SILENT then NOOUTPUT {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_silent_elm327 first SILENT then ELM327 {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_silent_toyota first SILENT then TOYOTA {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_nooutput_silent first NOOUTPUT then SILENT {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_nooutput_nooutput first NOOUTPUT then NOOUTPUT {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_nooutput_elm327 first NOOUTPUT then ELM327 {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_nooutput_toyota first NOOUTPUT then TOYOTA {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_elm327_silent first ELM327 then SILENT {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_elm327_nooutput first ELM327 then NOOUTPUT {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_elm327_elm327 first ELM327 then ELM327 {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m4_elm327_toyota first ELM327 then TOYOTA {
            doc /* M4: 0xdc (m, p) */
            @RecordTransition { id = "M4"; trigger = "0xdc (m, p)"; condition = "m ∈ {SILENT, NOOUTPUT, ELM327}, or m = TOYOTA with p = 73"; effect = "reset state; relay per m"; build = "reference"; swsr = ("SWSR-512", "SWSR-104a"); gap = ""; code = "panda board/reference_lock.h:25-27; main_comms.h:74-78"; }
        }
        transition m5_toyota_silent first TOYOTA then SILENT {
            doc /* M5: 0xdc (m, p) */
            @RecordTransition { id = "M5"; trigger = "0xdc (m, p)"; condition = "m ∈ {NOOUTPUT, SILENT}"; effect = "reset state; relay released"; build = "reference"; swsr = ("SWSR-512"); gap = ""; code = "panda board/reference_lock.h:22-24; main_comms.h:74-78"; }
        }
        transition m5_toyota_nooutput first TOYOTA then NOOUTPUT {
            doc /* M5: 0xdc (m, p) */
            @RecordTransition { id = "M5"; trigger = "0xdc (m, p)"; condition = "m ∈ {NOOUTPUT, SILENT}"; effect = "reset state; relay released"; build = "reference"; swsr = ("SWSR-512"); gap = ""; code = "panda board/reference_lock.h:22-24; main_comms.h:74-78"; }
        }
        transition m6_silent_silent first SILENT then SILENT {
            doc /* M6: 0xdc (m, p) */
            @RecordTransition { id = "M6"; trigger = "0xdc (m, p)"; condition = "any other (m, p)"; effect = "request refused, counted in requests_rejected_pkt"; build = "reference"; swsr = ("SWSR-512", "SWSR-513"); gap = ""; code = "panda board/reference_lock.h:53-58; main_comms.h:74-78 (request mapped to 0x00)"; }
        }
        transition m6_nooutput_nooutput first NOOUTPUT then NOOUTPUT {
            doc /* M6: 0xdc (m, p) */
            @RecordTransition { id = "M6"; trigger = "0xdc (m, p)"; condition = "any other (m, p)"; effect = "request refused, counted in requests_rejected_pkt"; build = "reference"; swsr = ("SWSR-512", "SWSR-513"); gap = ""; code = "panda board/reference_lock.h:53-58; main_comms.h:74-78 (request mapped to 0x00)"; }
        }
        transition m6_elm327_elm327 first ELM327 then ELM327 {
            doc /* M6: 0xdc (m, p) */
            @RecordTransition { id = "M6"; trigger = "0xdc (m, p)"; condition = "any other (m, p)"; effect = "request refused, counted in requests_rejected_pkt"; build = "reference"; swsr = ("SWSR-512", "SWSR-513"); gap = ""; code = "panda board/reference_lock.h:53-58; main_comms.h:74-78 (request mapped to 0x00)"; }
        }
        transition m6_toyota_toyota first TOYOTA then TOYOTA {
            doc /* M6: 0xdc (m, p) */
            @RecordTransition { id = "M6"; trigger = "0xdc (m, p)"; condition = "any other (m, p)"; effect = "request refused, counted in requests_rejected_pkt"; build = "reference"; swsr = ("SWSR-512", "SWSR-513"); gap = ""; code = "panda board/reference_lock.h:53-58; main_comms.h:74-78 (request mapped to 0x00)"; }
        }
        transition m6_other_car_other_car first OTHER_CAR then OTHER_CAR {
            doc /* M6: 0xdc (m, p) */
            @RecordTransition { id = "M6"; trigger = "0xdc (m, p)"; condition = "any other (m, p)"; effect = "request refused, counted in requests_rejected_pkt"; build = "reference"; swsr = ("SWSR-512", "SWSR-513"); gap = ""; code = "panda board/reference_lock.h:53-58; main_comms.h:74-78 (request mapped to 0x00)"; }
        }
        transition m7_toyota_silent first TOYOTA then SILENT {
            doc /* M7: 1 Hz tick */
            @RecordTransition { id = "M7"; trigger = "1 Hz tick"; condition = "heartbeat counter ≥ 5 (ignition on) / 2 (off)"; effect = "siren if recently engaged; heartbeat_lost"; build = "all"; swsr = ("SWSR-510", "SWSR-516"); gap = ""; code = "panda main.c:237-257"; }
        }
        transition m7_other_car_silent first OTHER_CAR then SILENT {
            doc /* M7: 1 Hz tick */
            @RecordTransition { id = "M7"; trigger = "1 Hz tick"; condition = "heartbeat counter ≥ 5 (ignition on) / 2 (off)"; effect = "siren if recently engaged; heartbeat_lost"; build = "all"; swsr = ("SWSR-510", "SWSR-516"); gap = ""; code = "panda main.c:237-257"; }
        }
        transition m8_silent_silent first SILENT then SILENT {
            doc /* M8: harness status change */
            @RecordTransition { id = "M8"; trigger = "harness status change"; condition = ""; effect = "set_safety_mode(current) (state reset)"; build = "all"; swsr = ("SWSR-311"); gap = ""; code = "panda main.c:176-183"; }
        }
        transition m8_nooutput_nooutput first NOOUTPUT then NOOUTPUT {
            doc /* M8: harness status change */
            @RecordTransition { id = "M8"; trigger = "harness status change"; condition = ""; effect = "set_safety_mode(current) (state reset)"; build = "all"; swsr = ("SWSR-311"); gap = ""; code = "panda main.c:176-183"; }
        }
        transition m8_elm327_elm327 first ELM327 then ELM327 {
            doc /* M8: harness status change */
            @RecordTransition { id = "M8"; trigger = "harness status change"; condition = ""; effect = "set_safety_mode(current) (state reset)"; build = "all"; swsr = ("SWSR-311"); gap = ""; code = "panda main.c:176-183"; }
        }
        transition m8_toyota_toyota first TOYOTA then TOYOTA {
            doc /* M8: harness status change */
            @RecordTransition { id = "M8"; trigger = "harness status change"; condition = ""; effect = "set_safety_mode(current) (state reset)"; build = "all"; swsr = ("SWSR-311"); gap = ""; code = "panda main.c:176-183"; }
        }
        transition m8_other_car_other_car first OTHER_CAR then OTHER_CAR {
            doc /* M8: harness status change */
            @RecordTransition { id = "M8"; trigger = "harness status change"; condition = ""; effect = "set_safety_mode(current) (state reset)"; build = "all"; swsr = ("SWSR-311"); gap = ""; code = "panda main.c:176-183"; }
        }
    }

    state def <'SM-SELFDRIVED'> SelfdrivedEngagementStateOpenpilotstate {
        doc /* selfdrived engagement state (OpenpilotState) */
        @StateRecord { file = "05-software/state-machines/sm-selfdrived.yaml"; units = ("host.selfdrived"); }
        entry; then disabled;
        state disabled;
        state preEnabled;
        state enabled;
        state softDisabling;
        state overriding;
        transition x1_preenabled_disabled first preEnabled then disabled {
            doc /* X1: update (100 Hz) */
            @RecordTransition { id = "X1"; trigger = "update (100 Hz)"; condition = "IMMEDIATE_DISABLE present"; effect = "IMMEDIATE_DISABLE alert"; build = "all"; swsr = ("SWSR-601", "SWSR-615", "SWSR-618", "SWSR-621", "SWSR-626", "SWSR-307h"); gap = ""; code = "openpilot selfdrived/state.py:27-29"; }
        }
        transition x1_enabled_disabled first enabled then disabled {
            doc /* X1: update (100 Hz) */
            @RecordTransition { id = "X1"; trigger = "update (100 Hz)"; condition = "IMMEDIATE_DISABLE present"; effect = "IMMEDIATE_DISABLE alert"; build = "all"; swsr = ("SWSR-601", "SWSR-615", "SWSR-618", "SWSR-621", "SWSR-626", "SWSR-307h"); gap = ""; code = "openpilot selfdrived/state.py:27-29"; }
        }
        transition x1_softdisabling_disabled first softDisabling then disabled {
            doc /* X1: update (100 Hz) */
            @RecordTransition { id = "X1"; trigger = "update (100 Hz)"; condition = "IMMEDIATE_DISABLE present"; effect = "IMMEDIATE_DISABLE alert"; build = "all"; swsr = ("SWSR-601", "SWSR-615", "SWSR-618", "SWSR-621", "SWSR-626", "SWSR-307h"); gap = ""; code = "openpilot selfdrived/state.py:27-29"; }
        }
        transition x1_overriding_disabled first overriding then disabled {
            doc /* X1: update (100 Hz) */
            @RecordTransition { id = "X1"; trigger = "update (100 Hz)"; condition = "IMMEDIATE_DISABLE present"; effect = "IMMEDIATE_DISABLE alert"; build = "all"; swsr = ("SWSR-601", "SWSR-615", "SWSR-618", "SWSR-621", "SWSR-626", "SWSR-307h"); gap = ""; code = "openpilot selfdrived/state.py:27-29"; }
        }
        transition x2_preenabled_disabled first preEnabled then disabled {
            doc /* X2: update (100 Hz) */
            @RecordTransition { id = "X2"; trigger = "update (100 Hz)"; condition = "USER_DISABLE present, no IMMEDIATE_DISABLE"; effect = "USER_DISABLE alert"; build = "all"; swsr = ("SWSR-302h"); gap = ""; code = "openpilot selfdrived/state.py:31-33"; }
        }
        transition x2_enabled_disabled first enabled then disabled {
            doc /* X2: update (100 Hz) */
            @RecordTransition { id = "X2"; trigger = "update (100 Hz)"; condition = "USER_DISABLE present, no IMMEDIATE_DISABLE"; effect = "USER_DISABLE alert"; build = "all"; swsr = ("SWSR-302h"); gap = ""; code = "openpilot selfdrived/state.py:31-33"; }
        }
        transition x2_softdisabling_disabled first softDisabling then disabled {
            doc /* X2: update (100 Hz) */
            @RecordTransition { id = "X2"; trigger = "update (100 Hz)"; condition = "USER_DISABLE present, no IMMEDIATE_DISABLE"; effect = "USER_DISABLE alert"; build = "all"; swsr = ("SWSR-302h"); gap = ""; code = "openpilot selfdrived/state.py:31-33"; }
        }
        transition x2_overriding_disabled first overriding then disabled {
            doc /* X2: update (100 Hz) */
            @RecordTransition { id = "X2"; trigger = "update (100 Hz)"; condition = "USER_DISABLE present, no IMMEDIATE_DISABLE"; effect = "USER_DISABLE alert"; build = "all"; swsr = ("SWSR-302h"); gap = ""; code = "openpilot selfdrived/state.py:31-33"; }
        }
        transition e1 first enabled then softDisabling {
            doc /* E1: update (100 Hz) */
            @RecordTransition { id = "E1"; trigger = "update (100 Hz)"; condition = "SOFT_DISABLE present, no IMMEDIATE_DISABLE or USER_DISABLE"; effect = "soft-disable timer = 3 s (300 cycles); SOFT_DISABLE alert"; build = "all"; swsr = ("SWSR-601", "SWSR-624"); gap = ""; code = "openpilot selfdrived/state.py:7, 38-41"; }
        }
        transition e2 first enabled then overriding {
            doc /* E2: update (100 Hz) */
            @RecordTransition { id = "E2"; trigger = "update (100 Hz)"; condition = "OVERRIDE_LATERAL or OVERRIDE_LONGITUDINAL present, no disable event"; effect = "override alerts"; build = "all"; swsr = ("SWSR-305h"); gap = ""; code = "openpilot selfdrived/state.py:43-45"; }
        }
        transition sd1 first softDisabling then enabled {
            doc /* SD1: update (100 Hz) */
            @RecordTransition { id = "SD1"; trigger = "update (100 Hz)"; condition = "SOFT_DISABLE no longer present, no IMMEDIATE_DISABLE or USER_DISABLE"; effect = "none"; build = "all"; swsr = ("SWSR-601"); gap = ""; code = "openpilot selfdrived/state.py:49-51"; }
        }
        transition sd2 first softDisabling then disabled {
            doc /* SD2: update (100 Hz) */
            @RecordTransition { id = "SD2"; trigger = "update (100 Hz)"; condition = "SOFT_DISABLE still present and the timer has run out (3 s after E1/O1)"; effect = "none"; build = "all"; swsr = ("SWSR-601", "SWSR-624"); gap = ""; code = "openpilot selfdrived/state.py:20, 53-57"; }
        }
        transition p1 first preEnabled then enabled {
            doc /* P1: update (100 Hz) */
            @RecordTransition { id = "P1"; trigger = "update (100 Hz)"; condition = "PRE_ENABLE no longer present, no disable event, no SOFT_DISABLE"; effect = "none"; build = "all"; swsr = ("SWSR-302i"); gap = ""; code = "openpilot selfdrived/state.py:60, 66-69"; }
        }
        transition p2 first preEnabled then disabled {
            doc /* P2: update (100 Hz) */
            @RecordTransition { id = "P2"; trigger = "update (100 Hz)"; condition = "SOFT_DISABLE present, no IMMEDIATE_DISABLE or USER_DISABLE (DQ-433 A)"; effect = "SOFT_DISABLE alert; engagement attempt ended"; build = "all"; swsr = ("SWSR-302i"); gap = ""; code = "openpilot selfdrived/state.py:60-65"; }
        }
        transition o1 first overriding then softDisabling {
            doc /* O1: update (100 Hz) */
            @RecordTransition { id = "O1"; trigger = "update (100 Hz)"; condition = "SOFT_DISABLE present, no IMMEDIATE_DISABLE or USER_DISABLE"; effect = "soft-disable timer = 3 s; SOFT_DISABLE alert"; build = "all"; swsr = ("SWSR-601", "SWSR-624"); gap = ""; code = "openpilot selfdrived/state.py:72-76"; }
        }
        transition o2 first overriding then enabled {
            doc /* O2: update (100 Hz) */
            @RecordTransition { id = "O2"; trigger = "update (100 Hz)"; condition = "no override event and no SOFT_DISABLE, no disable event"; effect = "none"; build = "all"; swsr = ("SWSR-305i"); gap = ""; code = "openpilot selfdrived/state.py:77-78"; }
        }
        transition n1 first disabled then disabled {
            doc /* N1: update (100 Hz) */
            @RecordTransition { id = "N1"; trigger = "update (100 Hz)"; condition = "ENABLE and NO_ENTRY present"; effect = "NO_ENTRY alert, engagement refused"; build = "all"; swsr = ("SWSR-514h", "SWSR-610", "SWSR-619", "SWSR-620", "SWSR-623"); gap = ""; code = "openpilot selfdrived/state.py:84-86"; }
        }
        transition d1 first disabled then preEnabled {
            doc /* D1: update (100 Hz) */
            @RecordTransition { id = "D1"; trigger = "update (100 Hz)"; condition = "ENABLE and PRE_ENABLE present, no NO_ENTRY"; effect = "ENABLE alert"; build = "all"; swsr = ("SWSR-514h", "SWSR-610", "SWSR-619", "SWSR-620", "SWSR-623"); gap = ""; code = "openpilot selfdrived/state.py:89-90, 95"; }
        }
        transition d2 first disabled then overriding {
            doc /* D2: update (100 Hz) */
            @RecordTransition { id = "D2"; trigger = "update (100 Hz)"; condition = "ENABLE and an override event present, no NO_ENTRY or PRE_ENABLE"; effect = "ENABLE alert"; build = "all"; swsr = ("SWSR-514h", "SWSR-610", "SWSR-619", "SWSR-620", "SWSR-623"); gap = ""; code = "openpilot selfdrived/state.py:91-92, 95"; }
        }
        transition d3 first disabled then enabled {
            doc /* D3: update (100 Hz) */
            @RecordTransition { id = "D3"; trigger = "update (100 Hz)"; condition = "ENABLE present, no NO_ENTRY, PRE_ENABLE or override event"; effect = "ENABLE alert"; build = "all"; swsr = ("SWSR-514h", "SWSR-610", "SWSR-619", "SWSR-620", "SWSR-623"); gap = ""; code = "openpilot selfdrived/state.py:93-95"; }
        }
    }

    state def <'SM-TOY-AUTH'> ToyotaAuthorityControlsAllowed {
        doc /* Toyota authority (controls_allowed) */
        @StateRecord { file = "05-software/state-machines/sm-toy-auth.yaml"; units = ("U-SAF-CORE", "U-SAF-TOY", "U-PND-MAIN"); }
        entry; then NOT_ALLOWED;
        state NOT_ALLOWED;
        state ENGAGE_PENDING;
        state ALLOWED;
        transition t1 first NOT_ALLOWED then ALLOWED {
            doc /* T1: 0x1D2 valid */
            @RecordTransition { id = "T1"; trigger = "0x1D2 valid"; condition = "CRUISE_ACTIVE 0→1 and rx_checks_allow_engagement() (every RX check valid; reference build also no TX-rate block); reference build also CRUISE_ACTIVE = 0 received since the safety mode was set, heartbeat engaged = 1 at the edge, and MAIN_ON = 1 (a grant while MAIN_ON = 0 is cleared in the same call)"; effect = "set"; build = "all"; swsr = ("SWSR-301", "SWSR-306", "SWSR-311", "SWSR-405", "SWSR-518"); gap = ""; code = "opendbc 98d3be1 safety.h:716-739 (pcm_cruise_check; reference build: the window opens and pcm_engage_check :476-488 grants at once), :420-438 (rx_checks_allow_engagement); modes/toyota.h:127-146, 271-274"; }
        }
        transition t1a first NOT_ALLOWED then ENGAGE_PENDING {
            doc /* T1a: 0x1D2 valid */
            @RecordTransition { id = "T1a"; trigger = "0x1D2 valid"; condition = "CRUISE_ACTIVE 0→1, rx_checks_allow_engagement(), CRUISE_ACTIVE = 0 received since the safety mode was set, heartbeat engaged = 0 at the edge, MAIN_ON = 1 (an edge while MAIN_ON = 0 opens the window and closes it in the same call, T8)"; effect = "open the 1 s window (pcm_engage_pending, pcm_engage_ts)"; build = "reference"; swsr = ("SWSR-301", "SWSR-306", "SWSR-311", "SWSR-405", "SWSR-518"); gap = ""; code = "opendbc 98d3be1 safety.h:725-735 (pcm_cruise_check); modes/toyota.h:127-146 (toyota_cruise_main_check, pcm_engage_cancel)"; }
        }
        transition t1b first ENGAGE_PENDING then ALLOWED {
            doc /* T1b: safety task (100 Hz) */
            @RecordTransition { id = "T1b"; trigger = "safety task (100 Hz)"; condition = "heartbeat engaged = 1 within 1 s of the edge, and rx_checks_allow_engagement()"; effect = "set, close the window"; build = "reference"; swsr = ("SWSR-301", "SWSR-306", "SWSR-405", "SWSR-518"); gap = ""; code = "opendbc 98d3be1 safety.h:476-488 (pcm_engage_check), :516 (from safety_tick)"; }
        }
        transition t1c first ENGAGE_PENDING then NOT_ALLOWED {
            doc /* T1c: safety task, 0x1D2 or any RX */
            @RecordTransition { id = "T1c"; trigger = "safety task, 0x1D2 or any RX"; condition = "1 s passed without heartbeat engaged = 1; or CRUISE_ACTIVE = 0; or brake rising, or pressed while moving; or an RX check lagging, below 10 Hz or invalid in the safety task; or heartbeat engaged = 1 while rx_checks_allow_engagement() is false; or (0x1D3 / 0x1D2) MAIN_ON = 0 with cruise active for more than 150 ms"; effect = "close the window"; build = "reference"; swsr = ("SWSR-301", "SWSR-302", "SWSR-306"); gap = ""; code = "opendbc 98d3be1 safety.h:476-488, :491-493 (pcm_engage_cancel), :512-515 (safety_tick), :718-723 (pcm_cruise_check), :533-539 (generic_rx_checks); modes/toyota.h:140-145"; }
        }
        transition t8 first NOT_ALLOWED then NOT_ALLOWED {
            doc /* T8: 0x1D2 valid */
            @RecordTransition { id = "T8"; trigger = "0x1D2 valid"; condition = "CRUISE_ACTIVE held 1; or 0→1 with rx_checks_allow_engagement() false; or (reference build) 0→1 before CRUISE_ACTIVE = 0 has been received in this safety mode, or 0→1 while MAIN_ON = 0 (refused at once; a window it opened is closed in the same call, SM-F1 fixed)"; effect = "none"; build = "all"; swsr = ("SWSR-301", "SWSR-306", "SWSR-311", "SWSR-405"); gap = ""; code = "opendbc 98d3be1 safety.h:716-739; modes/toyota.h:127-146, 271-274"; }
        }
        transition t2 first ALLOWED then NOT_ALLOWED {
            doc /* T2: 0x1D2 valid */
            @RecordTransition { id = "T2"; trigger = "0x1D2 valid"; condition = "CRUISE_ACTIVE = 0"; effect = "clear"; build = "all"; swsr = ("SWSR-301"); gap = ""; code = "opendbc 98d3be1 safety.h:718-723 (pcm_cruise_check; reference build also closes the window)"; }
        }
        transition t3 first ALLOWED then NOT_ALLOWED {
            doc /* T3: any RX */
            @RecordTransition { id = "T3"; trigger = "any RX"; condition = "brake rising, or pressed while moving"; effect = "clear"; build = "all"; swsr = ("SWSR-302"); gap = ""; code = "opendbc 98d3be1 safety.h:533-539 (generic_rx_checks)"; }
        }
        transition t4 first ALLOWED then NOT_ALLOWED {
            doc /* T4: RX of checked message */
            @RecordTransition { id = "T4"; trigger = "RX of checked message"; condition = "checksum, quality flag or counter invalid; reference build: or a frame of another length (ATC-25), the entry then invalid until a frame of the right length"; effect = "clear"; build = "all"; swsr = ("SWSR-402", "SWSR-406"); gap = ""; code = "opendbc 62b89a3 safety.h:114-129 (is_msg_valid), :178-197 (rx_length_check, reference build, modes with rx_timeout_periods), :236-241; upstream build: a frame of another length matches no entry and is ignored"; }
        }
        transition t5 first ALLOWED then NOT_ALLOWED {
            doc /* T5: safety_tick (100 Hz safety task) */
            @RecordTransition { id = "T5"; trigger = "safety_tick (100 Hz safety task)"; condition = "any RX check lagging (5 periods), below 10 Hz, or invalid"; effect = "clear"; build = "all"; swsr = ("SWSR-401", "SWSR-401a", "SWSR-406"); gap = ""; code = "opendbc 98d3be1 safety.h:497-509 (safety_tick); panda main.c:133 (safety_task_handler)"; }
        }
        transition t6 first ALLOWED then NOT_ALLOWED {
            doc /* T6: 1 Hz tick */
            @RecordTransition { id = "T6"; trigger = "1 Hz tick"; condition = "heartbeat engaged=0 for 3 consecutive ticks"; effect = "clear"; build = "all"; swsr = ""; gap = "upstream backstop, 2-3 s: does not meet the 0.3 s of SWSR-307; in the reference build T6a revokes first"; code = "panda f4803c5 main.c:261-269 (tick_handler)"; }
        }
        transition t6a first ALLOWED then NOT_ALLOWED {
            doc /* T6a: safety task: engaged-mismatch check */
            @RecordTransition { id = "T6a"; trigger = "safety task: engaged-mismatch check"; condition = "heartbeat engaged=0 for 30 safety tasks (0.3 s) since the first such heartbeat while authority was granted"; effect = "clear; siren 3 s when PCM cruise is still active 0.5 s after that heartbeat (SWSR-516b)"; build = "reference"; swsr = ("SWSR-307", "SWSR-516b"); gap = ""; code = "panda f4803c5 main.c:152-168 (safety_task_handler), drivers/engaged_mismatch.h"; }
        }
        transition t7_not_allowed_not_allowed first NOT_ALLOWED then NOT_ALLOWED {
            doc /* T7: safety mode set (0xdc, heartbeat loss, harness change) */
            @RecordTransition { id = "T7"; trigger = "safety mode set (0xdc, heartbeat loss, harness change)"; condition = ""; effect = "clear"; build = "all"; swsr = ("SWSR-311"); gap = ""; code = "opendbc 98d3be1 safety.h:574, 641-648 (set_safety_hooks; also clears the window, the TX-rate block and the cruise edge memory)"; }
        }
        transition t7_engage_pending_not_allowed first ENGAGE_PENDING then NOT_ALLOWED {
            doc /* T7: safety mode set (0xdc, heartbeat loss, harness change) */
            @RecordTransition { id = "T7"; trigger = "safety mode set (0xdc, heartbeat loss, harness change)"; condition = ""; effect = "clear"; build = "all"; swsr = ("SWSR-311"); gap = ""; code = "opendbc 98d3be1 safety.h:574, 641-648 (set_safety_hooks; also clears the window, the TX-rate block and the cruise edge memory)"; }
        }
        transition t7_allowed_not_allowed first ALLOWED then NOT_ALLOWED {
            doc /* T7: safety mode set (0xdc, heartbeat loss, harness change) */
            @RecordTransition { id = "T7"; trigger = "safety mode set (0xdc, heartbeat loss, harness change)"; condition = ""; effect = "clear"; build = "all"; swsr = ("SWSR-311"); gap = ""; code = "opendbc 98d3be1 safety.h:574, 641-648 (set_safety_hooks; also clears the window, the TX-rate block and the cruise edge memory)"; }
        }
        transition t9 first ALLOWED then NOT_ALLOWED {
            doc /* T9: TX frame rejected by a content check */
            @RecordTransition { id = "T9"; trigger = "TX frame rejected by a content check"; condition = ""; effect = "clear, reason"; build = "all"; swsr = ("SWSR-108"); gap = ""; code = "not implemented: the frame is dropped, authority kept (opendbc safety.h safety_tx_hook)"; }
        }
        transition t10a first ALLOWED then NOT_ALLOWED {
            doc /* T10a: safety task: heartbeat check */
            @RecordTransition { id = "T10a"; trigger = "safety task: heartbeat check"; condition = "no SoC heartbeat for > 0.3 s in a car mode"; effect = "clear; siren 3 s when authority was granted (panda c33343b)"; build = "all"; swsr = ("SWSR-407", "SWSR-516"); gap = ""; code = "panda main.c:135-137 (heartbeat_monitor_tick); heartbeat_siren.h at panda c33343b"; }
        }
        transition t10b first ALLOWED then NOT_ALLOWED {
            doc /* T10b: safety task: command freshness check */
            @RecordTransition { id = "T10b"; trigger = "safety task: command freshness check"; condition = "no accepted 0x2E4/0x343 for 50/100 ms (accepted: passed by the TX hook; supervision starts at the first safety task that finds authority granted)"; effect = "clear, reason"; build = "reference"; swsr = ("SWSR-408"); gap = ""; code = "opendbc 27f20db safety.h:288-297 (tx_arrival_update, noted only for a frame the TX hook accepts, :362-367), :492-508 (tx_arrival_ok), :562-564; modes/toyota.h:608-613; no reason is reported"; }
        }
        transition t10c first ALLOWED then NOT_ALLOWED {
            doc /* T10c: 0x1D2 / 0x1D3 */
            @RecordTransition { id = "T10c"; trigger = "0x1D2 / 0x1D3"; condition = "CRUISE_ACTIVE while MAIN_ON is off for > 150 ms"; effect = "clear"; build = "reference"; swsr = ("SWSR-405"); gap = ""; code = "opendbc modes/toyota.h:126-143 (toyota_cruise_main_check)"; }
        }
        transition t10d first ALLOWED then NOT_ALLOWED {
            doc /* T10d: platform fault */
            @RecordTransition { id = "T10d"; trigger = "platform fault"; condition = ""; effect = "clear, SS-S"; build = "all"; swsr = ("SWSR-502"); gap = ""; code = "not implemented: faults are reported only"; }
        }
        transition t10e first ALLOWED then NOT_ALLOWED {
            doc /* T10e: driver steering override */
            @RecordTransition { id = "T10e"; trigger = "driver steering override"; condition = ""; effect = "clear, reason"; build = "all"; swsr = ("SWSR-304"); gap = ""; code = "not implemented for Toyota LKA"; }
        }
        transition t11 first ALLOWED then NOT_ALLOWED {
            doc /* T11: TX frame over the per-ID rate budget */
            @RecordTransition { id = "T11"; trigger = "TX frame over the per-ID rate budget"; condition = "3 rejected frames in one 125 ms half-window"; effect = "clear, report txRateExceeded"; build = "reference"; swsr = ("SWSR-518"); gap = ""; code = "opendbc 98d3be1 safety.h:263-292 (tx_rate_check; reference build also blocks re-engagement for one clean 250 ms window, ATC-20)"; }
        }
        transition t12 first ALLOWED then NOT_ALLOWED {
            doc /* T12: safety task: driver torque check */
            @RecordTransition { id = "T12"; trigger = "safety task: driver torque check"; condition = "|driver torque| > T_ovr for > t_ovr"; effect = "clear (steering_disengage)"; build = "all"; swsr = ("SWSR-304a"); gap = ""; code = "not implemented for Toyota LKA"; }
        }
        transition t13 first ALLOWED then NOT_ALLOWED {
            doc /* T13: SPI error */
            @RecordTransition { id = "T13"; trigger = "SPI error"; condition = "more than N_spi errors within 100 ms"; effect = "clear, report"; build = "all"; swsr = ("SWSR-413"); gap = ""; code = "not implemented: errors are counted only (panda drivers/spi.h)"; }
        }
        transition t14 first ALLOWED then NOT_ALLOWED {
            doc /* T14: car-side CAN bus-off or persistent TX failure */
            @RecordTransition { id = "T14"; trigger = "car-side CAN bus-off or persistent TX failure"; condition = ""; effect = "clear, report"; build = "all"; swsr = ("SWSR-508"); gap = ""; code = "not implemented: counted only (panda drivers/fdcan.h)"; }
        }
        transition t15 first ALLOWED then NOT_ALLOWED {
            doc /* T15: safety task: forwarding supervision */
            @RecordTransition { id = "T15"; trigger = "safety task: forwarding supervision"; condition = "relay driven and no camera-side frame for > t_fwd, or camera-side bus-off"; effect = "clear all, release relay"; build = "all"; swsr = ("SWSR-711"); gap = ""; code = "not implemented"; }
        }
    }
}
