// GENERATED by assurance/models/sysml/tools/gen_requirements.py from the work products. Do not edit;
// change the work product and regenerate (README §7).

package LionDriverNeeds {
    doc /* Stakeholders, stakeholder needs and use cases of WP-S-01 §1.2–§1.4 (ASPICE SYS.1). Each need is refined
           by the SYS requirements and safety goals named in its row, written as a derivation from the need; each
           use case serves the needs its objective requires and performs the functions of WP-C-01 §2.1 it uses. */

    private import ScalarValues::*;
    private import RequirementDerivation::*;
    private import LionDriverLibrary::*;
    private import LionDriverArchitecture::*;
    private import LionDriverFunctions::*;
    private import LionDriverRequirements::*;

    // stakeholders and actors (§1.2)
    part def Driver :> Person { doc /* The licensed driver who engages LD-SDA and supervises it at all times (SAE Level 2; WP-C-02 §4.2) */ }
    part def Occupants :> Person { doc /* The passengers in the car */ }
    part def OtherRoadUsers :> Person { doc /* Drivers, riders and pedestrians around the car */ }
    part def Owner :> Person { doc /* The person who installs the device, keeps the car as AOU-08…AOU-10 require, and decides when the software changes */ }
    part def ProjectLead :> Person { doc /* The maintainer and safety authority: releases, field monitoring and the evidence behind them */ }
    part def Vehicle :> ExternalElement { doc /* The reference car's own systems that the item commands or reads: steering, engine, brakes, collision braking, cluster (WP-C-01 §3.2) */ }

    requirement def StakeholderNeed {
        doc /* A need of one or more stakeholders (WP-S-01 §1.3), in their words rather than as a requirement. */
        subject ldsda : LdSda;
        attribute workProduct : String;
        attribute source : String;
    }

    // stakeholder needs (§1.3)
    requirement <'SN-01'> sn_01 : StakeholderNeed {
        doc /* Less effort keeping the car in its lane on a highway, while staying in charge of the steering */
        subject :>> ldsda;
        stakeholder driver : Driver;
        :>> workProduct = "WP-S-01";
        :>> source = "WP-C-01 §2.1 (F-01); WP-C-02 §4.1";
    }
    requirement <'SN-02'> sn_02 : StakeholderNeed {
        doc /* Help with a lane change, but only when the driver asks for it */
        subject :>> ldsda;
        stakeholder driver : Driver;
        :>> workProduct = "WP-S-01";
        :>> source = "WP-C-02 §4.1 (F-01)";
    }
    requirement <'SN-03'> sn_03 : StakeholderNeed {
        doc /* A set speed and a chosen gap to the car ahead, also when stopping and moving off in a queue */
        subject :>> ldsda;
        stakeholder driver : Driver;
        :>> workProduct = "WP-S-01";
        :>> source = "WP-C-02 §4.1 (F-02)";
    }
    requirement <'SN-04'> sn_04 : StakeholderNeed {
        doc /* Switching the assistance on and off with the car's own controls, and taking over at any moment by braking, steering or accelerating */
        subject :>> ldsda;
        stakeholder driver : Driver;
        :>> workProduct = "WP-S-01";
        :>> source = "WP-C-02 §4.1 (F-03); WP-C-03 §6";
    }
    requirement <'SN-05'> sn_05 : StakeholderNeed {
        doc /* Assistance only where it was assured: on highways inside the ODD, at highway speed and with the assured settings */
        subject :>> ldsda;
        stakeholder projectLead : ProjectLead;
        :>> workProduct = "WP-S-01";
        :>> source = "WP-C-02 §3; DQ-023, DQ-221, DQ-280";
    }
    requirement <'SN-06'> sn_06 : StakeholderNeed {
        doc /* Knowing at all times whether the assistance is on, and why it asks the driver to take over */
        subject :>> ldsda;
        stakeholder driver : Driver;
        :>> workProduct = "WP-S-01";
        :>> source = "WP-C-02 §4.1 (F-05); WP-C-08";
    }
    requirement <'SN-07'> sn_07 : StakeholderNeed {
        doc /* A warning of an imminent collision or of drifting out of the lane, also when the assistance is off */
        subject :>> ldsda;
        stakeholder driver : Driver;
        :>> workProduct = "WP-S-01";
        :>> source = "WP-C-02 §4.1 (F-06, F-07)";
    }
    requirement <'SN-08'> sn_08 : StakeholderNeed {
        doc /* A driver who stays attentive while assisted, and a car that slows down safely if the driver does not respond */
        subject :>> ldsda;
        stakeholder otherRoadUsers : OtherRoadUsers;
        :>> workProduct = "WP-S-01";
        :>> source = "WP-C-02 §4.2; WP-C-03 §6";
    }
    requirement <'SN-09'> sn_09 : StakeholderNeed {
        doc /* The item never moves the car in a way the driver cannot control, and never weakens the car's own safety functions */
        subject :>> ldsda;
        stakeholder occupants : Occupants;
        stakeholder otherRoadUsers : OtherRoadUsers;
        :>> workProduct = "WP-S-01";
        :>> source = "WP-C-03 §6";
    }
    requirement <'SN-10'> sn_10 : StakeholderNeed {
        doc /* Assistance that is ready soon after starting and does not drop out without cause */
        subject :>> ldsda;
        stakeholder driver : Driver;
        :>> workProduct = "WP-S-01";
        :>> source = "WP-C-02 §4.1";
    }
    requirement <'SN-11'> sn_11 : StakeholderNeed {
        doc /* Every drive recorded and tied to the software that ran, so that incidents can be analysed */
        subject :>> ldsda;
        stakeholder projectLead : ProjectLead;
        :>> workProduct = "WP-S-01";
        :>> source = "WP-C-01 §2.1 (F-09); WP-O-04";
    }
    requirement <'SN-12'> sn_12 : StakeholderNeed {
        doc /* Control over what leaves the car and when its software changes */
        subject :>> ldsda;
        stakeholder owner : Owner;
        :>> workProduct = "WP-S-01";
        :>> source = "WP-S-07 §3.6, §3.7; DQ-121";
    }

    // refinement of each need by system requirements and safety goals
    #derivation connection {
        end #original ::> sn_01;
        end #derive ::> sys_001;
    }
    #derivation connection {
        end #original ::> sn_01;
        end #derive ::> sys_002;
    }
    #derivation connection {
        end #original ::> sn_01;
        end #derive ::> sys_003;
    }
    #derivation connection {
        end #original ::> sn_01;
        end #derive ::> sys_007;
    }
    #derivation connection {
        end #original ::> sn_01;
        end #derive ::> sys_008;
    }
    #derivation connection {
        end #original ::> sn_02;
        end #derive ::> sys_005;
    }
    #derivation connection {
        end #original ::> sn_02;
        end #derive ::> sys_006;
    }
    #derivation connection {
        end #original ::> sn_03;
        end #derive ::> sys_020;
    }
    #derivation connection {
        end #original ::> sn_03;
        end #derive ::> sys_021;
    }
    #derivation connection {
        end #original ::> sn_03;
        end #derive ::> sys_022;
    }
    #derivation connection {
        end #original ::> sn_03;
        end #derive ::> sys_023;
    }
    #derivation connection {
        end #original ::> sn_03;
        end #derive ::> sys_024;
    }
    #derivation connection {
        end #original ::> sn_03;
        end #derive ::> sys_025;
    }
    #derivation connection {
        end #original ::> sn_03;
        end #derive ::> sys_026;
    }
    #derivation connection {
        end #original ::> sn_04;
        end #derive ::> sys_040;
    }
    #derivation connection {
        end #original ::> sn_04;
        end #derive ::> sys_042;
    }
    #derivation connection {
        end #original ::> sn_04;
        end #derive ::> sg_05;
    }
    #derivation connection {
        end #original ::> sn_05;
        end #derive ::> sys_021;
    }
    #derivation connection {
        end #original ::> sn_05;
        end #derive ::> sys_027;
    }
    #derivation connection {
        end #original ::> sn_05;
        end #derive ::> sys_040;
    }
    #derivation connection {
        end #original ::> sn_05;
        end #derive ::> sys_041;
    }
    #derivation connection {
        end #original ::> sn_06;
        end #derive ::> sys_004;
    }
    #derivation connection {
        end #original ::> sn_06;
        end #derive ::> sys_080;
    }
    #derivation connection {
        end #original ::> sn_06;
        end #derive ::> sys_081;
    }
    #derivation connection {
        end #original ::> sn_06;
        end #derive ::> sys_082;
    }
    #derivation connection {
        end #original ::> sn_06;
        end #derive ::> sys_083;
    }
    #derivation connection {
        end #original ::> sn_07;
        end #derive ::> sys_100;
    }
    #derivation connection {
        end #original ::> sn_07;
        end #derive ::> sys_101;
    }
    #derivation connection {
        end #original ::> sn_07;
        end #derive ::> sys_102;
    }
    #derivation connection {
        end #original ::> sn_08;
        end #derive ::> sys_060;
    }
    #derivation connection {
        end #original ::> sn_08;
        end #derive ::> sys_061;
    }
    #derivation connection {
        end #original ::> sn_08;
        end #derive ::> sys_062;
    }
    #derivation connection {
        end #original ::> sn_08;
        end #derive ::> sys_063;
    }
    #derivation connection {
        end #original ::> sn_08;
        end #derive ::> sg_08;
    }
    #derivation connection {
        end #original ::> sn_09;
        end #derive ::> sg_01;
    }
    #derivation connection {
        end #original ::> sn_09;
        end #derive ::> sg_02;
    }
    #derivation connection {
        end #original ::> sn_09;
        end #derive ::> sg_03;
    }
    #derivation connection {
        end #original ::> sn_09;
        end #derive ::> sg_04;
    }
    #derivation connection {
        end #original ::> sn_09;
        end #derive ::> sg_06;
    }
    #derivation connection {
        end #original ::> sn_09;
        end #derive ::> sg_07;
    }
    #derivation connection {
        end #original ::> sn_10;
        end #derive ::> sys_043;
    }
    #derivation connection {
        end #original ::> sn_10;
        end #derive ::> sys_120;
    }
    #derivation connection {
        end #original ::> sn_10;
        end #derive ::> sys_145;
    }
    #derivation connection {
        end #original ::> sn_11;
        end #derive ::> sys_121;
    }
    #derivation connection {
        end #original ::> sn_11;
        end #derive ::> sys_140;
    }
    #derivation connection {
        end #original ::> sn_11;
        end #derive ::> sys_141;
    }
    #derivation connection {
        end #original ::> sn_11;
        end #derive ::> sys_142;
    }
    #derivation connection {
        end #original ::> sn_11;
        end #derive ::> sys_143;
    }
    #derivation connection {
        end #original ::> sn_12;
        end #derive ::> sys_144;
    }
    #derivation connection {
        end #original ::> sn_12;
        end #derive ::> sys_145;
    }

    use case def ItemUseCase {
        doc /* A use of LD-SDA, its subject, by its actors (WP-S-01 §1.4). */
        subject ldsda : LdSda;
    }

    // use cases (§1.4)
    use case <'UC-01'> uc_01 : ItemUseCase {
        doc /* Keep the lane on a highway */
        subject :>> ldsda;
        actor driver : Driver;
        actor vehicle : Vehicle;
        objective {
            doc /* The item steers the car near the lane centre, through curves down to R_ODD, while the driver keeps eyes on the road and hands near the wheel */
            require sn_01;
        }
        perform lateralControl;
        perform driverInformation;
        perform safetyEnvelope;
    }
    use case <'UC-02'> uc_02 : ItemUseCase {
        doc /* Change lanes on request */
        subject :>> ldsda;
        actor driver : Driver;
        actor vehicle : Vehicle;
        objective {
            doc /* The driver checks the next lane, signals and nudges the wheel; the item moves the car over within 10 s, or cancels when the signal is released */
            require sn_02;
        }
        perform lateralControl;
        perform safetyEnvelope;
    }
    use case <'UC-03'> uc_03 : ItemUseCase {
        doc /* Cruise and follow */
        subject :>> ldsda;
        actor driver : Driver;
        actor vehicle : Vehicle;
        objective {
            doc /* The item holds the set speed, then follows a slower car ahead at the chosen gap */
            require sn_03;
        }
        perform longitudinalControl;
        perform safetyEnvelope;
    }
    use case <'UC-04'> uc_04 : ItemUseCase {
        doc /* Stop and go in a queue */
        subject :>> ldsda;
        actor driver : Driver;
        actor vehicle : Vehicle;
        objective {
            doc /* The item stops behind a stopping car, holds the car, and moves off when the car ahead does; with no car ahead, the driver moves off */
            require sn_03;
        }
        perform longitudinalControl;
        perform safetyEnvelope;
    }
    use case <'UC-05'> uc_05 : ItemUseCase {
        doc /* Engage */
        subject :>> ldsda;
        actor driver : Driver;
        actor vehicle : Vehicle;
        objective {
            doc /* The driver sets cruise with the car's controls; the item takes control only inside the ODD, at highway speed and with the assured settings, and otherwise refuses with a no-entry alert */
            require sn_04;
            require sn_05;
            require sn_10;
        }
        perform engagement;
        perform driverInformation;
        perform safetyEnvelope;
    }
    use case <'UC-06'> uc_06 : ItemUseCase {
        doc /* Take over */
        subject :>> ldsda;
        actor driver : Driver;
        actor vehicle : Vehicle;
        objective {
            doc /* The driver brakes, cancels, steers or accelerates; the item releases control at once on brake or cancel, and lets the driver override on steering or accelerator */
            require sn_04;
            require sn_09;
        }
        perform engagement;
        perform safetyEnvelope;
    }
    use case <'UC-07'> uc_07 : ItemUseCase {
        doc /* Hand back at a limit */
        subject :>> ldsda;
        actor driver : Driver;
        objective {
            doc /* At a curve beyond the item's authority, a fault or the edge of the ODD, the item warns, says why, and hands control back */
            require sn_06;
            require sn_09;
            require sn_10;
        }
        perform engagement;
        perform driverInformation;
        perform safetyEnvelope;
    }
    use case <'UC-08'> uc_08 : ItemUseCase {
        doc /* Warn when not assisted */
        subject :>> ldsda;
        actor driver : Driver;
        objective {
            doc /* With the assistance off, the item warns of a predicted collision or of a drift towards a lane line */
            require sn_07;
        }
        perform driverInformation;
        perform forwardCollisionWarning;
        perform laneDepartureWarning;
    }
    use case <'UC-09'> uc_09 : ItemUseCase {
        doc /* Keep the driver attentive */
        subject :>> ldsda;
        actor driver : Driver;
        objective {
            doc /* The item watches the driver; on distraction it escalates its alerts, and with no response it slows the car, disengages and locks out */
            require sn_08;
        }
        perform longitudinalControl;
        perform driverMonitoring;
        perform driverInformation;
    }
    use case <'UC-10'> uc_10 : ItemUseCase {
        doc /* Record and review a drive */
        subject :>> ldsda;
        actor driver : Driver;
        actor projectLead : ProjectLead;
        objective {
            doc /* Every drive is logged with the software that ran; the driver can flag a moment; the project lead reviews the logs for field monitoring */
            require sn_11;
        }
        perform loggingAndUpdate;
    }
    use case <'UC-11'> uc_11 : ItemUseCase {
        doc /* Install and update */
        subject :>> ldsda;
        actor owner : Owner;
        objective {
            doc /* The owner installs the device and installs each release by hand; nothing is uploaded or updated while driving unless the policy allows it */
            require sn_12;
        }
        perform loggingAndUpdate;
    }
}
