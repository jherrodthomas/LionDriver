// GENERATED by assurance/models/sysml/tools/gen_requirements.py from the work products. Do not edit;
// change the work product and regenerate (README §7).

package LionDriverRequirements {
    doc /* Requirements copied from the work products; see tools/gen_requirements.py. */

    private import ScalarValues::*;
    private import RequirementDerivation::*;

    requirement def LionDriverRequirement {
        doc /* Common attributes: the work product the requirement is copied from, and its allocation text as written there. */
        attribute workProduct : String;
        attribute allocText : String;
    }
    requirement def SafetyGoal :> LionDriverRequirement {
        doc /* Safety goal of the HARA (WP-C-03 §6). */
        attribute asil : String;
        attribute safeState : String;
        attribute ftti : String;
    }
    requirement def FunctionalSafetyRequirement :> LionDriverRequirement {
        doc /* Functional safety requirement of the FSC (WP-C-04 §5). */
        attribute asil : String;
        attribute verifMethod : String;
    }
    requirement def TechnicalSafetyRequirement :> LionDriverRequirement {
        doc /* Technical safety requirement (WP-S-02, WP-S-06 for TSR-8xx). */
        attribute asil : String;
        attribute mechanism : String;
        attribute timing : String;
        attribute verifMethod : String;
    }
    requirement def SystemRequirement :> LionDriverRequirement {
        doc /* Functional and performance requirement of the intended functionality (WP-S-01 §2–§9). */
        attribute functionId : String;
        attribute reqType : String;
        attribute target : String;
        attribute verifMethod : String;
    }
    requirement def CybersecurityRequirement :> LionDriverRequirement {
        doc /* Detailed cybersecurity requirement (WP-S-07 §4). */
        attribute group : String;
        attribute groupTitle : String;
        attribute safetyRelation : String;
        attribute verifMethod : String;
        attribute status : String;   // in, partly, not, check (WP-S-07 Figure 4-1)
    }

    requirement <'SG-01'> sg_01 : SafetyGoal {
        doc /* The item shall not cause lateral motion of the vehicle that exceeds what the driver can control, including any steering actuation while the item is not engaged */
        :>> workProduct = "WP-C-03";
        :>> allocText = "";
        :>> asil = "C";
        :>> safeState = "LKA torque request zero, steer request bit cleared; driver informed";
        :>> ftti = "≤ 0.5 s (preliminary)";
    }
    requirement <'SG-02'> sg_02 : SafetyGoal {
        doc /* The item shall not lose or degrade lateral control while engaged without giving the driver an adequate take-over warning */
        :>> workProduct = "WP-C-03";
        :>> allocText = "";
        :>> asil = "C";
        :>> safeState = "Driver warned (visual + acoustic) and lateral control handed back with a smooth torque ramp-down";
        :>> ftti = "≤ 1 s from fault to warning (preliminary)";
    }
    requirement <'SG-03'> sg_03 : SafetyGoal {
        doc /* The item shall not cause unintended vehicle acceleration */
        :>> workProduct = "WP-C-03";
        :>> allocText = "";
        :>> asil = "C";
        :>> safeState = "Acceleration request ≤ 0 (no positive acceleration); ACC cancelled to the PCM";
        :>> ftti = "≤ 1 s (preliminary)";
    }
    requirement <'SG-04'> sg_04 : SafetyGoal {
        doc /* The item shall not cause deceleration that exceeds what following traffic and the driver can control */
        :>> workProduct = "WP-C-03";
        :>> allocText = "";
        :>> asil = "B";
        :>> safeState = "Deceleration limited; transition to \"inactive\" (no ACC command; coast) with a bounded jerk";
        :>> ftti = "≤ 1 s (preliminary)";
    }
    requirement <'SG-05'> sg_05 : SafetyGoal {
        doc /* The item shall release control immediately when the driver brakes, cancels, or overrides steering */
        :>> workProduct = "WP-C-03";
        :>> allocText = "";
        :>> asil = "B";
        :>> safeState = "Disengaged: no lateral or longitudinal actuation";
        :>> ftti = "≤ 0.2 s from driver input to release (preliminary)";
    }
    requirement <'SG-06'> sg_06 : SafetyGoal {
        doc /* The item shall not lose longitudinal deceleration capability while engaged without giving the driver an adequate take-over warning */
        :>> workProduct = "WP-C-03";
        :>> allocText = "";
        :>> asil = "C";
        :>> safeState = "Driver warned; ACC cancelled so that the driver brakes";
        :>> ftti = "≤ 1 s (preliminary)";
    }
    requirement <'SG-07'> sg_07 : SafetyGoal {
        doc /* The item shall not suppress, delay or alter the vehicle's stock pre-collision (PCS/AEB) function */
        :>> workProduct = "WP-C-03";
        :>> allocText = "";
        :>> asil = "B";
        :>> safeState = "Camera PCS messages forwarded unchanged; if forwarding cannot be guaranteed (e.g. harness fault), relay released to restore the stock camera link";
        :>> ftti = "≤ 0.2 s for loss or delay of forwarding (preliminary, WP-S-04 §3.6); content: per frame";
    }
    requirement <'SG-08'> sg_08 : SafetyGoal {
        doc /* The item shall not continue automated control while the driver is not supervising or not responding without escalating to a minimal-risk reaction */
        :>> workProduct = "WP-C-03";
        :>> allocText = "";
        :>> asil = "A";
        :>> safeState = "Escalating take-over alerts; on no response, the no-response reaction (DQ-365 A, WP-C-04 FSR-02.09): steering stays on while the vehicle decelerates in lane to a standstill, stays stopped and held, and cannot drive off or be re-engaged until the driver responds. The hold rests on the PCM (AOU-16, not yet tested)";
        :>> ftti = "≤ 6 s from loss of attention to the first alert (preliminary)";
    }
    requirement <'FSR-01.01'> fsr_01_01 : FunctionalSafetyRequirement {
        doc /* The envelope shall limit the commanded LKA torque magnitude to a speed-dependent bound derived from driver controllability (lateral acceleration and lateral deviation reached within the FTTI). */
        :>> workProduct = "WP-C-04";
        :>> allocText = "E-03";
        :>> asil = "C";
        :>> verifMethod = "A, T-SIL, T-VEH";
    }
    requirement <'FSR-01.02'> fsr_01_02 : FunctionalSafetyRequirement {
        doc /* The envelope shall limit the rate of change of the commanded LKA torque (rise per frame and over a real-time window) to bounds derived from controllability. A fall toward zero is not limited, as it is the safe direction for SG-01; a bounded ramp of torque withdrawn on a fault is FSR-02.04. */
        :>> workProduct = "WP-C-04";
        :>> allocText = "E-03";
        :>> asil = "C";
        :>> verifMethod = "A, T-SIL";
    }
    requirement <'FSR-01.03'> fsr_01_03 : FunctionalSafetyRequirement {
        doc /* The envelope shall limit the commanded LKA torque to within a bounded difference of the measured EPS motor torque. */
        :>> workProduct = "WP-C-04";
        :>> allocText = "E-03";
        :>> asil = "C";
        :>> verifMethod = "T-SIL";
    }
    requirement <'FSR-01.04'> fsr_01_04 : FunctionalSafetyRequirement {
        doc /* The envelope shall block any non-zero LKA torque or set steer-request bit while lateral authority is not granted. */
        :>> workProduct = "WP-C-04";
        :>> allocText = "E-03";
        :>> asil = "C";
        :>> verifMethod = "T-SIL, T-HIL";
    }
    requirement <'FSR-01.05'> fsr_01_05 : FunctionalSafetyRequirement {
        doc /* The envelope shall grant actuation authority only on a driver engagement action confirmed by the vehicle (rising edge of PCM cruise active) and shall revoke it when PCM cruise becomes inactive. */
        :>> workProduct = "WP-C-04";
        :>> allocText = "E-03";
        :>> asil = "C";
        :>> verifMethod = "T-SIL, T-VEH";
    }
    requirement <'FSR-01.06'> fsr_01_06 : FunctionalSafetyRequirement {
        doc /* The envelope shall detect loss, corruption, repetition and staleness of each RX signal it uses for gating or limiting (PCM cruise state, brake, gas, driver/EPS torque, wheel speed) and revoke actuation authority within the FTTI allocation of §8. */
        :>> workProduct = "WP-C-04";
        :>> allocText = "E-03";
        :>> asil = "C";
        :>> verifMethod = "T-SIL, FI";
    }
    requirement <'FSR-01.07'> fsr_01_07 : FunctionalSafetyRequirement {
        doc /* The envelope shall detect missing or stale control commands from the SoC and remove actuation within the FTTI allocation of §8. */
        :>> workProduct = "WP-C-04";
        :>> allocText = "E-03";
        :>> asil = "C";
        :>> verifMethod = "T-HIL, FI";
    }
    requirement <'FSR-01.08'> fsr_01_08 : FunctionalSafetyRequirement {
        doc /* The envelope shall detect corruption, loss and reordering of command frames received from the SoC and discard affected frames. */
        :>> workProduct = "WP-C-04";
        :>> allocText = "E-03";
        :>> asil = "C";
        :>> verifMethod = "T-HIL, FI";
    }
    requirement <'FSR-01.09'> fsr_01_09 : FunctionalSafetyRequirement {
        doc /* The safety MCU shall detect its own execution faults (program-flow hang, clock failure, memory corruption, register corruption) and enter the safe state (no actuation TX, relay released) within the FTTI allocation of §8. */
        :>> workProduct = "WP-C-04";
        :>> allocText = "E-03 (HW+SW)";
        :>> asil = "C";
        :>> verifMethod = "A (FMEDA), FI";
    }
    requirement <'FSR-01.10'> fsr_01_10 : FunctionalSafetyRequirement {
        doc /* The safety mode and safety parameter for the reference configuration shall be fixed in the envelope and shall not be changeable by the SoC while a car safety mode is active; debug-only commands shall be unavailable in release builds; and the SoC shall not be able to make the safety MCU run non-release code or drive the relay outside the envelope through its reset and boot lines (GAP-38, refined by TSR-511). */
        :>> workProduct = "WP-C-04";
        :>> allocText = "E-03";
        :>> asil = "C";
        :>> verifMethod = "R, T-HIL";
    }
    requirement <'FSR-01.11'> fsr_01_11 : FunctionalSafetyRequirement {
        doc /* The envelope shall detect a harness relay malfunction (camera control messages seen on the car side) and inhibit all actuation TX. */
        :>> workProduct = "WP-C-04";
        :>> allocText = "E-03, E-05";
        :>> asil = "C";
        :>> verifMethod = "T-SIL, T-HIL";
    }
    requirement <'FSR-01.12'> fsr_01_12 : FunctionalSafetyRequirement {
        doc /* On any detected fault affecting lateral actuation, the envelope shall enter the lateral safe state (torque 0, steer request cleared) and keep it until a new valid engagement. */
        :>> workProduct = "WP-C-04";
        :>> allocText = "E-03";
        :>> asil = "C";
        :>> verifMethod = "T-SIL, FI";
    }
    requirement <'FSR-01.13'> fsr_01_13 : FunctionalSafetyRequirement {
        doc /* The EPS shall limit LKA torque to an overpowerable level and shall end LKA torque within a bounded time after 0x2E4 stops or carries the request bit cleared. (External measure, AOU-01R) */
        :>> workProduct = "WP-C-04";
        :>> allocText = "EXT-EPS";
        :>> asil = "— (ext.)";
        :>> verifMethod = "T-VEH";
    }
    requirement <'FSR-01.14'> fsr_01_14 : FunctionalSafetyRequirement {
        doc /* The SoC controller shall command lateral motion with a margin below every envelope limit (target: commanded lateral acceleration ≤ 3.0 m/s², jerk ≤ 5 m/s³, torque ≤ 90 % of the envelope bound). */
        :>> workProduct = "WP-C-04";
        :>> allocText = "E-01";
        :>> asil = "QM";
        :>> verifMethod = "T-SIL";
    }
    requirement <'FSR-02.01'> fsr_02_01 : FunctionalSafetyRequirement {
        doc /* The item shall detect EPS conditions that remove or reduce LKA assistance (EPS LKA fault states) while engaged. */
        :>> workProduct = "WP-C-04";
        :>> allocText = "E-03 (detection), E-01 (diagnosis text)";
        :>> asil = "C";
        :>> verifMethod = "T-SIL, T-VEH";
    }
    requirement <'FSR-02.02'> fsr_02_02 : FunctionalSafetyRequirement {
        doc /* The item shall detect loss of the inputs that the lateral command depends on (driving model output, calibration, localization, vehicle state) and shall not continue to actuate on inputs that are no longer valid. */
        :>> workProduct = "WP-C-04";
        :>> allocText = "E-01 (QM, see note), E-03 (FSR-01.07 as backstop)";
        :>> asil = "C";
        :>> verifMethod = "T-SIL, FI";
    }
    requirement <'FSR-02.03'> fsr_02_03 : FunctionalSafetyRequirement {
        doc /* On a detected loss or degradation of lateral control, the item shall give a visual and acoustic take-over request within 1 s of fault detection and before or at the start of torque reduction. */
        :>> workProduct = "WP-C-04";
        :>> allocText = "E-01/HMI, E-03 siren for SoC loss";
        :>> asil = "C";
        :>> verifMethod = "T-HIL, T-VEH";
    }
    requirement <'FSR-02.04'> fsr_02_04 : FunctionalSafetyRequirement {
        doc /* When torque is withdrawn because of a fault (not a driver action), the reduction shall follow a bounded ramp unless the fault makes the command itself untrusted, in which case torque shall go to zero at once. */
        :>> workProduct = "WP-C-04";
        :>> allocText = "E-01, E-03";
        :>> asil = "C";
        :>> verifMethod = "A, T-SIL";
    }
    requirement <'FSR-02.05'> fsr_02_05 : FunctionalSafetyRequirement {
        doc /* When granted actuation authority ends for a reason other than a driver action that the safety MCU itself observes, the safety MCU shall give an acoustic warning that does not depend on the SoC. This covers the loss of communication with the SoC or of its commands, a fault the safety MCU detects, a disengagement reported by the SoC whose cruise cancel had no effect, and a reset of the safety MCU (watchdog or fault reset) that interrupts granted authority. The reset case was added 2026-10-14 (DQ-054: the engaged state is kept across the reset; TSR-516(d)); the trigger was widened 2026-10-21 to match TSR-516(b)/(c) (DQ-404 A; cancel-lag guard, lead 2026-10-21). */
        :>> workProduct = "WP-C-04";
        :>> allocText = "E-03 (panda buzzer)";
        :>> asil = "C";
        :>> verifMethod = "T-HIL";
    }
    requirement <'FSR-02.06'> fsr_02_06 : FunctionalSafetyRequirement {
        doc /* Driver monitoring shall detect an inattentive or unresponsive driver while engaged and escalate warnings within the timing set in WP-C-08 (assurance/02-concept/WP-C-08-driver-hmi-misuse-analysis.md) §5. */
        :>> workProduct = "WP-C-04";
        :>> allocText = "E-01/DM, E-02";
        :>> asil = "A";
        :>> verifMethod = "T-SIL, T-VEH";
    }
    requirement <'FSR-02.07'> fsr_02_07 : FunctionalSafetyRequirement {
        doc /* Driver monitoring shall detect its own invalidity (no driver image, camera blocked, model output missing or not credible) and fall back to a policy that is no less strict than the active policy. */
        :>> workProduct = "WP-C-04";
        :>> allocText = "E-01/DM";
        :>> asil = "A";
        :>> verifMethod = "T-SIL, FI";
    }
    requirement <'FSR-02.08'> fsr_02_08 : FunctionalSafetyRequirement {
        doc /* Driver monitoring shall not be disabled, put into demo mode or replaced by synthetic inputs while the item can engage. */
        :>> workProduct = "WP-C-04";
        :>> allocText = "E-01/DM";
        :>> asil = "A";
        :>> verifMethod = "R, T-SIL";
    }
    requirement <'FSR-02.09'> fsr_02_09 : FunctionalSafetyRequirement {
        doc /* If the driver does not respond to the highest DM warning, the item shall decelerate the vehicle in a controlled way in its lane to a standstill, keep it stopped and held, and prevent the item from driving off again or being re-engaged until the driver responds; after the driver responds, the lockout period applies. This is the SG-08 safe state (WP-C-03 v0.4), decided 2026-10-16, DQ-365 A: steering stays on while the vehicle decelerates in lane to a standstill within the envelope limits with the alert sounding; the vehicle then stays stopped and held, and the item cannot drive off again: re-engagement and resumption are locked out until the driver responds. Lateral and longitudinal control shall not stay active at the set speed. */
        :>> workProduct = "WP-C-04";
        :>> allocText = "E-01/DM";
        :>> asil = "A";
        :>> verifMethod = "T-SIL, T-VEH";
    }
    requirement <'FSR-02.10'> fsr_02_10 : FunctionalSafetyRequirement {
        doc /* The item shall detect that the envelope does not grant actuation authority while the SoC is engaged (envelope blocking, stuck authority, safety-mode mismatch) and give a take-over request within the SG-02/SG-06 warning budget (§8). */
        :>> workProduct = "WP-C-04";
        :>> allocText = "E-01 (detection, alert), E-03 (reports authority state)";
        :>> asil = "C";
        :>> verifMethod = "T-SIL, FI";
    }
    requirement <'FSR-02.11'> fsr_02_11 : FunctionalSafetyRequirement {
        doc /* The item shall detect failure of the HMI path that shows the engagement state and gives take-over requests (display, sound) and treat it as a fault leading to disengagement with the SoC-independent indications (FSR-02.05 buzzer, FSR-05.05 cluster cruise state). */
        :>> workProduct = "WP-C-04";
        :>> allocText = "E-01/HMI, E-03";
        :>> asil = "C";
        :>> verifMethod = "T-SIL, FI";
    }
    requirement <'FSR-02.12'> fsr_02_12 : FunctionalSafetyRequirement {
        doc /* Before granting engagement, and while the item can engage, the item shall read the stored diagnostic trouble codes of the EPS and of the brake and stability control, and shall not allow engagement while a code that affects lateral or longitudinal control is set; the driver shall be told why. (Decided 2026-10-14, DQ-056: replaces reliance on the driver's dashboard lamp check, WP-O-02 OPS-01.) */
        :>> workProduct = "WP-C-04";
        :>> allocText = "E-01";
        :>> asil = "QM (supports FSR-02.01, FSR-06.03)";
        :>> verifMethod = "T-SIL, T-VEH";
    }
    requirement <'FSR-03.01'> fsr_03_01 : FunctionalSafetyRequirement {
        doc /* The envelope shall limit the commanded acceleration to an upper bound derived from controllability for the reference vehicle. */
        :>> workProduct = "WP-C-04";
        :>> allocText = "E-03";
        :>> asil = "C";
        :>> verifMethod = "A, T-SIL, T-VEH";
    }
    requirement <'FSR-03.02'> fsr_03_02 : FunctionalSafetyRequirement {
        doc /* The envelope shall allow only the inactive acceleration value while longitudinal authority is not granted or while the driver presses the accelerator. */
        :>> workProduct = "WP-C-04";
        :>> allocText = "E-03";
        :>> asil = "C";
        :>> verifMethod = "T-SIL";
    }
    requirement <'FSR-03.03'> fsr_03_03 : FunctionalSafetyRequirement {
        doc /* The envelope shall limit the rate of increase of commanded acceleration (jerk). */
        :>> workProduct = "WP-C-04";
        :>> allocText = "E-03";
        :>> asil = "C";
        :>> verifMethod = "T-SIL";
    }
    requirement <'FSR-03.04'> fsr_03_04 : FunctionalSafetyRequirement {
        doc /* FSR-01.05…01.12 apply to the longitudinal path (shared mechanisms; see trace §9). */
        :>> workProduct = "WP-C-04";
        :>> allocText = "E-03";
        :>> asil = "C";
        :>> verifMethod = "as referenced";
    }
    requirement <'FSR-03.05'> fsr_03_05 : FunctionalSafetyRequirement {
        doc /* On a detected fault affecting longitudinal control, the item shall stop requesting positive acceleration and request ACC cancel from the PCM. */
        :>> workProduct = "WP-C-04";
        :>> allocText = "E-03 (inactive value), E-01 (cancel)";
        :>> asil = "C";
        :>> verifMethod = "T-SIL, T-VEH";
    }
    requirement <'FSR-03.06'> fsr_03_06 : FunctionalSafetyRequirement {
        doc /* The PCM shall bound ACC acceleration requests to its own envelope and honour the cancel request. (External measure, AOU-05R) */
        :>> workProduct = "WP-C-04";
        :>> allocText = "EXT-PCM";
        :>> asil = "— (ext.)";
        :>> verifMethod = "T-VEH";
    }
    requirement <'FSR-04.01'> fsr_04_01 : FunctionalSafetyRequirement {
        doc /* The envelope shall limit the commanded deceleration to a bound derived from following-traffic controllability. */
        :>> workProduct = "WP-C-04";
        :>> allocText = "E-03";
        :>> asil = "B";
        :>> verifMethod = "A, T-SIL";
    }
    requirement <'FSR-04.02'> fsr_04_02 : FunctionalSafetyRequirement {
        doc /* The envelope shall limit the onset rate of commanded deceleration (negative jerk). */
        :>> workProduct = "WP-C-04";
        :>> allocText = "E-03";
        :>> asil = "B";
        :>> verifMethod = "T-SIL";
    }
    requirement <'FSR-04.03'> fsr_04_03 : FunctionalSafetyRequirement {
        doc /* The transition to the longitudinal safe state shall not create a deceleration step larger than the jerk bound of FSR-04.02. */
        :>> workProduct = "WP-C-04";
        :>> allocText = "E-01, E-03";
        :>> asil = "B";
        :>> verifMethod = "A, T-VEH";
    }
    requirement <'FSR-04.04'> fsr_04_04 : FunctionalSafetyRequirement {
        doc /* Driver accelerator input shall override commanded deceleration. */
        :>> workProduct = "WP-C-04";
        :>> allocText = "E-03, EXT-PCM";
        :>> asil = "B";
        :>> verifMethod = "T-SIL, T-VEH";
    }
    requirement <'FSR-04.05'> fsr_04_05 : FunctionalSafetyRequirement {
        doc /* Deceleration that the item initiates for a reason other than following traffic shall be announced by a visual and acoustic alert, ahead of its onset for the driver-monitoring no-response and at the latest at its onset for a fault soft disable (DQ-407 A: that slow-down is mild, and holding it back keeps the fault active), and shall stay within the bounds of FSR-04.01/04.02. */
        :>> workProduct = "WP-C-04";
        :>> allocText = "E-01 (alert), E-03 (bounds)";
        :>> asil = "B";
        :>> verifMethod = "T-SIL, T-VEH";
    }
    requirement <'FSR-04.06'> fsr_04_06 : FunctionalSafetyRequirement {
        doc /* Forward collision warnings shall be raised only from valid, fresh inputs, and the false-warning rate in the ODD shall be bounded so that driver reflex braking with a close follower is not a credible consequence. */
        :>> workProduct = "WP-C-04";
        :>> allocText = "E-01";
        :>> asil = "A";
        :>> verifMethod = "T-SIL, validation (WP-V-02)";
    }
    requirement <'FSR-05.01'> fsr_05_01 : FunctionalSafetyRequirement {
        doc /* The envelope shall revoke all actuation authority on a driver brake press (rising edge, or pressed while moving) within the SG-05 FTTI. */
        :>> workProduct = "WP-C-04";
        :>> allocText = "E-03";
        :>> asil = "B";
        :>> verifMethod = "T-SIL, T-VEH";
    }
    requirement <'FSR-05.02'> fsr_05_02 : FunctionalSafetyRequirement {
        doc /* The envelope shall revoke all actuation authority when the PCM reports cruise inactive (cancel, main switch off). */
        :>> workProduct = "WP-C-04";
        :>> allocText = "E-03";
        :>> asil = "B";
        :>> verifMethod = "T-SIL, T-VEH";
    }
    requirement <'FSR-05.03'> fsr_05_03 : FunctionalSafetyRequirement {
        doc /* The envelope shall detect driver steering override (driver torque above a threshold) and reduce the LKA torque toward zero at a bounded rate so it does not oppose the driver, for as long as the override lasts; the item shall show the driver that the override was noticed. (Decided 2026-10-14, DQ-053: back off on override and show a cue.) */
        :>> workProduct = "WP-C-04";
        :>> allocText = "E-03, E-01/HMI (cue)";
        :>> asil = "B";
        :>> verifMethod = "T-SIL, T-VEH";
    }
    requirement <'FSR-05.04'> fsr_05_04 : FunctionalSafetyRequirement {
        doc /* The envelope shall block positive acceleration while the accelerator is pressed. */
        :>> workProduct = "WP-C-04";
        :>> allocText = "E-03";
        :>> asil = "B";
        :>> verifMethod = "T-SIL";
    }
    requirement <'FSR-05.05'> fsr_05_05 : FunctionalSafetyRequirement {
        doc /* The engagement state that the envelope enforces shall equal the PCM cruise state, so that the vehicle's own cruise indicator gives the driver an indication of engagement independent of the item's HMI. */
        :>> workProduct = "WP-C-04";
        :>> allocText = "E-03, EXT-CLU";
        :>> asil = "C";
        :>> verifMethod = "A, T-VEH";
    }
    requirement <'FSR-05.06'> fsr_05_06 : FunctionalSafetyRequirement {
        doc /* If PCM cruise is active while the item is not engaged (or the reverse) for longer than a bounded time, the item shall warn the driver and request cancel. */
        :>> workProduct = "WP-C-04";
        :>> allocText = "E-01, E-03";
        :>> asil = "C";
        :>> verifMethod = "T-SIL";
    }
    requirement <'FSR-05.07'> fsr_05_07 : FunctionalSafetyRequirement {
        doc /* Driver brake input shall produce braking regardless of ACC commands. (External measure, AOU-03R) */
        :>> workProduct = "WP-C-04";
        :>> allocText = "EXT-PCM";
        :>> asil = "— (ext.)";
        :>> verifMethod = "T-VEH";
    }
    requirement <'FSR-06.01'> fsr_06_01 : FunctionalSafetyRequirement {
        doc /* The item shall detect loss or staleness of the longitudinal plan, lead information (radar/vision) and model output while engaged. */
        :>> workProduct = "WP-C-04";
        :>> allocText = "E-01 (QM), E-03 backstop via FSR-01.07";
        :>> asil = "C";
        :>> verifMethod = "T-SIL, FI";
    }
    requirement <'FSR-06.02'> fsr_06_02 : FunctionalSafetyRequirement {
        doc /* On detected loss, the item shall give a take-over request within 1 s and cancel ACC so that control returns to the driver; it shall not hold a stale acceleration command. */
        :>> workProduct = "WP-C-04";
        :>> allocText = "E-01, E-03";
        :>> asil = "C";
        :>> verifMethod = "T-SIL, T-VEH";
    }
    requirement <'FSR-06.03'> fsr_06_03 : FunctionalSafetyRequirement {
        doc /* The item shall detect that the PCM does not execute ACC (ACC fault, cruise fault) and warn the driver. */
        :>> workProduct = "WP-C-04";
        :>> allocText = "E-01";
        :>> asil = "C";
        :>> verifMethod = "T-SIL";
    }
    requirement <'FSR-06.04'> fsr_06_04 : FunctionalSafetyRequirement {
        doc /* Non-finite or out-of-range actuator commands shall be treated as faults with a fault reaction, not silently replaced. */
        :>> workProduct = "WP-C-04";
        :>> allocText = "E-01, E-03";
        :>> asil = "C";
        :>> verifMethod = "T-SIL";
    }
    requirement <'FSR-06.05'> fsr_06_05 : FunctionalSafetyRequirement {
        doc /* FSR-02.05 (independent acoustic warning on SoC loss) and FSR-02.06…02.09 (DM) also serve SG-06. */
        :>> workProduct = "WP-C-04";
        :>> allocText = "as ref.";
        :>> asil = "as ref.";
        :>> verifMethod = "as ref.";
    }
    requirement <'FSR-07.01'> fsr_07_01 : FunctionalSafetyRequirement {
        doc /* The item shall forward all camera-side messages to the car side unchanged, except the defined set of intercepted control messages. */
        :>> workProduct = "WP-C-04";
        :>> allocText = "E-03";
        :>> asil = "B";
        :>> verifMethod = "T-SIL, T-HIL";
    }
    requirement <'FSR-07.02'> fsr_07_02 : FunctionalSafetyRequirement {
        doc /* The item shall not originate any message that the stock PCS function uses (e.g. PRE_COLLISION 0x344, PCS_HUD 0x411, AEB 0x283 with content) in the reference configuration. */
        :>> workProduct = "WP-C-04";
        :>> allocText = "E-03";
        :>> asil = "B";
        :>> verifMethod = "R, T-SIL";
    }
    requirement <'FSR-07.03'> fsr_07_03 : FunctionalSafetyRequirement {
        doc /* On safety-MCU fault, loss of device power, or harness fault, the relay shall return to the stock camera-to-vehicle connection. */
        :>> workProduct = "WP-C-04";
        :>> allocText = "E-05, E-03";
        :>> asil = "B";
        :>> verifMethod = "A, T-HIL";
    }
    requirement <'FSR-07.04'> fsr_07_04 : FunctionalSafetyRequirement {
        doc /* openpilot longitudinal commands shall not prevent PCS braking from taking priority in the PCM. (External measure, AOU-04R) */
        :>> workProduct = "WP-C-04";
        :>> allocText = "EXT-PCM";
        :>> asil = "— (ext.)";
        :>> verifMethod = "T-VEH";
    }
    requirement <'FSR-07.05'> fsr_07_05 : FunctionalSafetyRequirement {
        doc /* The item shall inform the driver when the stock system reports an AEB or FCW event. */
        :>> workProduct = "WP-C-04";
        :>> allocText = "E-01";
        :>> asil = "QM";
        :>> verifMethod = "T-SIL";
    }
    requirement <'FSR-07.06'> fsr_07_06 : FunctionalSafetyRequirement {
        doc /* If the harness cannot return to the stock camera-to-vehicle connection (switch or relay stuck in intercept, detected by state readback), the item shall inhibit all actuation, warn the driver that stock PCS/AEB is unavailable, and refuse engagement until the harness is repaired. (Accepted 2026-10-14 as the degraded state, DQ-064; applies once readback exists.) */
        :>> workProduct = "WP-C-04";
        :>> allocText = "E-03 (detection), E-05 (readback), E-01/HMI (warning)";
        :>> asil = "B";
        :>> verifMethod = "T-HIL, FI";
    }
    requirement <'FSR-07.07'> fsr_07_07 : FunctionalSafetyRequirement {
        doc /* While the stock system reports an AEB event, the item shall request zero acceleration from the PCM (no added drive), so that stock AEB braking does not depend on PCM arbitration alone. FSR-07.04 and its AOU-04R test still apply. (Decided 2026-10-18, DQ-300 A; System FMEA SFM-036, SFM-ACT-020; FTA MCS-07.10.) */
        :>> workProduct = "WP-C-04";
        :>> allocText = "E-01";
        :>> asil = "QM (no ASIL claim; FSR-07.04 stays the measure)";
        :>> verifMethod = "T-SIL, T-VEH";
    }
    requirement <'FSR-08.01'> fsr_08_01 : FunctionalSafetyRequirement {
        doc /* While engaged, the item shall give the first driver alert within 6 s of the loss of attention, measured end to end from the driver's change of state to the alert (including camera frame time, DM model latency and policy timers), and shall reach the no-response reaction of FSR-02.09 within the time set in WP-S-04 (assurance/03-system/WP-S-04-timing-ftti-budget.md). */
        :>> workProduct = "WP-C-04";
        :>> allocText = "E-01/DM, E-01/HMI";
        :>> asil = "A";
        :>> verifMethod = "T-SIL, T-VEH";
    }
    requirement <'TSR-101'> tsr_101 : TechnicalSafetyRequirement {
        doc /* The envelope shall reject every STEERING_LKA (0x2E4) frame whose STEER_TORQUE_CMD magnitude exceeds the torque bound τ_max(v) of TSR-102. Until TSR-102 is implemented, τ_max is the baseline 1500 raw. */
        :>> workProduct = "WP-S-02";
        :>> allocText = "P-SW";
        :>> asil = "B‡";
        :>> mechanism = "LIM";
        :>> timing = "per frame / frame rejected (then TSR-108, TSR-109)";
        :>> verifMethod = "A, T-SIL, T-VEH";
    }
    requirement <'TSR-102'> tsr_102 : TechnicalSafetyRequirement {
        doc /* τ_max(v) shall be a speed-dependent lookup derived on the reference vehicle by (1) characterising the steady-state lateral acceleration and wheel torque produced by raw requests 0…1500 at speeds 10…120 km/h (AOU-01R), (2) choosing per speed the largest request whose worst-case lateral deviation over the driver intervention time stays inside the bound of WP-S-04 §3 (assurance/03-system/WP-S-04-timing-ftti-budget.md), and (3) confirming controllability C1 for that bound with the tests of WP-C-08 (assurance/02-concept/WP-C-08-driver-hmi-misuse-analysis.md) §8. The speed value used shall be the one that yields the smaller torque bound when the speed estimate is uncertain. */
        :>> workProduct = "WP-S-02";
        :>> allocText = "P-SW (+ calibration data, WP-W-09 (assurance/05-software/WP-W-09-configuration-calibration-data.md))";
        :>> asil = "B‡";
        :>> mechanism = "LIM";
        :>> timing = "per frame";
        :>> verifMethod = "A, T-SIL, T-VEH";
    }
    requirement <'TSR-103'> tsr_103 : TechnicalSafetyRequirement {
        doc /* The envelope shall reject a 0x2E4 frame whose torque lies outside [min(r, 0) − Δ, max(r, 0) + Δ], where r is the previous frame's torque and Δ = Δ_up for the frame rate check, or r is the torque at the start of the current real-time window and Δ = Δ_rt for the window check; the window restarts with the first frame more than 250 ms after its start. So a rise in magnitude, or a crossing of zero, by more than Δ (from r or from 0) is rejected, and these two checks accept any change toward zero: a fall toward zero is the safe direction for SG-01, and a bounded ramp of torque withdrawn on a fault is FSR-02.04's. While the command exceeds the measured EPS torque by more than Δ_meas, it shall fall by at least Δ_down per frame (TSR-104). A frame still beyond that bound after a smaller fall toward zero is rejected. After a rejected frame, or while authority is not granted, the reference for these checks is 0. The values shall be derived from the onset rate accepted in the controllability tests; the baseline values are Δ_up 15 and Δ_down 25 raw per frame and Δ_rt 450 raw per 250 ms. */
        :>> workProduct = "WP-S-02";
        :>> allocText = "P-SW";
        :>> asil = "B‡";
        :>> mechanism = "LIM";
        :>> timing = "per frame";
        :>> verifMethod = "A, T-SIL";
    }
    requirement <'TSR-104'> tsr_104 : TechnicalSafetyRequirement {
        doc /* The envelope shall reject 0x2E4 frames whose torque exceeds the measured EPS motor torque (0x260 STEER_TORQUE_EPS scaled by the EPS factor of the safety parameter) by more than Δ_meas (measured from 0 when the measured torque is of the opposite sign), using the minimum/maximum of the last 6 samples widened by 1 raw, unless the frame falls toward zero by at least Δ_down from the previous frame (TSR-103). Baseline Δ_meas = 350 raw. */
        :>> workProduct = "WP-S-02";
        :>> allocText = "P-SW";
        :>> asil = "B‡";
        :>> mechanism = "LIM, PLB";
        :>> timing = "per frame";
        :>> verifMethod = "T-SIL";
    }
    requirement <'TSR-105'> tsr_105 : TechnicalSafetyRequirement {
        doc /* While lateral authority is not granted, the envelope shall reject every 0x2E4 frame with non-zero torque or with STEER_REQUEST set. */
        :>> workProduct = "WP-S-02";
        :>> allocText = "P-SW";
        :>> asil = "B‡";
        :>> mechanism = "GATE";
        :>> timing = "per frame";
        :>> verifMethod = "T-SIL, T-HIL";
    }
    requirement <'TSR-106'> tsr_106 : TechnicalSafetyRequirement {
        doc /* While authority is granted, the envelope shall accept STEER_REQUEST = 0 with non-zero torque for at most 1 consecutive frame, only after ≥ 17 consecutive valid frames and ≥ 162 ms after the previous cut. */
        :>> workProduct = "WP-S-02";
        :>> allocText = "P-SW";
        :>> asil = "B‡";
        :>> mechanism = "GATE";
        :>> timing = "per frame";
        :>> verifMethod = "T-SIL";
    }
    requirement <'TSR-107'> tsr_107 : TechnicalSafetyRequirement {
        doc /* In the reference configuration (LKA torque path) the envelope shall reject any STEERING_LTA (0x191) frame that carries a steering request, a non-zero angle command or a non-zero torque wind-down, and shall accept 0x2E4 only with its specified length (5 bytes). */
        :>> workProduct = "WP-S-02";
        :>> allocText = "P-SW";
        :>> asil = "B‡";
        :>> mechanism = "GATE";
        :>> timing = "per frame";
        :>> verifMethod = "T-SIL";
    }
    requirement <'TSR-108'> tsr_108 : TechnicalSafetyRequirement {
        doc /* If the envelope rejects a lateral command frame while lateral authority is granted, it shall revoke lateral authority (SS-L) and keep it revoked until a new valid engagement (TSR-301), and it shall report the event and its cause to the SoC. */
        :>> workProduct = "WP-S-02";
        :>> allocText = "P-SW";
        :>> asil = "B‡";
        :>> mechanism = "FR";
        :>> timing = "detect: same frame / react: same frame";
        :>> verifMethod = "T-SIL, FI";
    }
    requirement <'TSR-109'> tsr_109 : TechnicalSafetyRequirement {
        doc /* Whenever the envelope rejects a 0x2E4 frame or revokes lateral authority, the EPS shall receive torque 0 with STEER_REQUEST 0 within ≤ 0.1 s. This shall be achieved by (a) the envelope transmitting, in place of each rejected frame, a 0x2E4 frame with zero torque, STEER_REQUEST 0, a counter continuing the host sequence and a valid checksum; or (b) only if vehicle characterisation shows that the EPS ramps LKA torque to zero within ≤ 0.1 s of a missing 0x2E4 frame, by withholding the frame. Option (a) is the recommended design. */
        :>> workProduct = "WP-S-02";
        :>> allocText = "P-SW (a); EXT (b)";
        :>> asil = "C";
        :>> mechanism = "FR";
        :>> timing = "react ≤ 0.1 s";
        :>> verifMethod = "T-HIL, T-VEH, FI";
    }
    requirement <'TSR-110'> tsr_110 : TechnicalSafetyRequirement {
        doc /* The envelope shall receive EPS_STATUS (0x262) and, while lateral authority is granted, shall revoke lateral authority and report the cause when LKA_STATE indicates an EPS fault or LKA unavailability, or when EPS_STATUS is missing beyond its timeout (TSR-401). The LKA_STATE fault code set shall be confirmed for the reference EPS firmware. */
        :>> workProduct = "WP-S-02";
        :>> allocText = "P-SW (detect); SoC (warn, TSR-606)";
        :>> asil = "C";
        :>> mechanism = "PLB, TMO";
        :>> timing = "detect ≤ 0.3 s / react ≤ 0.1 s";
        :>> verifMethod = "T-SIL, T-VEH";
    }
    requirement <'TSR-111'> tsr_111 : TechnicalSafetyRequirement {
        doc /* The EPS shall limit the LKA torque at the steering wheel to ≤ T_EPS for any 0x2E4 request and remove LKA torque within t_EPS after 0x2E4 stops or STEER_REQUEST clears. (External measure; T_EPS and t_EPS to be measured.) */
        :>> workProduct = "WP-S-02";
        :>> allocText = "EXT";
        :>> asil = "ext";
        :>> mechanism = "EXTM";
        :>> timing = "t_EPS TBD";
        :>> verifMethod = "T-VEH";
    }
    requirement <'TSR-201'> tsr_201 : TechnicalSafetyRequirement {
        doc /* The envelope shall reject every ACC_CONTROL (0x343) frame whose ACCEL_CMD exceeds a_max, where a_max is derived from the controllability of HE-03.1…03.3 on the reference vehicle. Baseline a_max = +2.0 m/s² (raw 2000). */
        :>> workProduct = "WP-S-02";
        :>> allocText = "P-SW";
        :>> asil = "C";
        :>> mechanism = "LIM";
        :>> timing = "per frame";
        :>> verifMethod = "A, T-SIL, T-VEH";
    }
    requirement <'TSR-202'> tsr_202 : TechnicalSafetyRequirement {
        doc /* The envelope shall reject every 0x343 frame whose ACCEL_CMD is below a_min, derived from the controllability of HE-04.1 (following traffic). Baseline a_min = −3.5 m/s² (raw −3500). */
        :>> workProduct = "WP-S-02";
        :>> allocText = "P-SW";
        :>> asil = "B";
        :>> mechanism = "LIM";
        :>> timing = "per frame";
        :>> verifMethod = "A, T-SIL, T-VEH";
    }
    requirement <'TSR-203'> tsr_203 : TechnicalSafetyRequirement {
        doc /* While longitudinal authority is not granted (not engaged, or accelerator pressed per TSR-305), the envelope shall accept 0x343 only with the inactive acceleration value. */
        :>> workProduct = "WP-S-02";
        :>> allocText = "P-SW";
        :>> asil = "C";
        :>> mechanism = "GATE";
        :>> timing = "per frame";
        :>> verifMethod = "T-SIL";
    }
    requirement <'TSR-204'> tsr_204 : TechnicalSafetyRequirement {
        doc /* The envelope shall reject 0x343 frames whose ACCEL_CMD increases, relative to the last accepted value (the inactive value counting as 0 m/s² at engagement), faster than j_up, derived from controllability. */
        :>> workProduct = "WP-S-02";
        :>> allocText = "P-SW";
        :>> asil = "C";
        :>> mechanism = "LIM";
        :>> timing = "per frame";
        :>> verifMethod = "T-SIL, T-VEH";
    }
    requirement <'TSR-205'> tsr_205 : TechnicalSafetyRequirement {
        doc /* The envelope shall reject 0x343 frames whose ACCEL_CMD decreases (deceleration onset) faster than j_down, derived from following-traffic controllability. */
        :>> workProduct = "WP-S-02";
        :>> allocText = "P-SW";
        :>> asil = "B";
        :>> mechanism = "LIM";
        :>> timing = "per frame";
        :>> verifMethod = "T-SIL, T-VEH";
    }
    requirement <'TSR-206'> tsr_206 : TechnicalSafetyRequirement {
        doc /* On revocation of longitudinal authority the transition to SS-G shall not cause a vehicle deceleration or acceleration step beyond the jerk bounds of TSR-204/205. If the PCM response to a step from the last commanded value to the inactive value is not shown to be bounded (AOU-05R), the envelope shall accept a commanded value that winds down to the inactive value at no more than j_down/j_up for at most 1 s after revocation. */
        :>> workProduct = "WP-S-02";
        :>> allocText = "P-SW, EXT";
        :>> asil = "C";
        :>> mechanism = "FR";
        :>> timing = "react ≤ 0.3 s to SS-G start";
        :>> verifMethod = "A, T-VEH";
    }
    requirement <'TSR-207'> tsr_207 : TechnicalSafetyRequirement {
        doc /* For 0x343, the envelope shall also check the actuation-relevant fields PERMIT_BRAKING, CANCEL_REQ, RELEASE_STANDSTILL and ACCEL_CMD_ALT against the values allowed in the current authority state, and while authority is not granted shall accept only frames that do not request acceleration, braking or standstill release. */
        :>> workProduct = "WP-S-02";
        :>> allocText = "P-SW";
        :>> asil = "C";
        :>> mechanism = "GATE";
        :>> timing = "per frame";
        :>> verifMethod = "T-SIL";
    }
    requirement <'TSR-208'> tsr_208 : TechnicalSafetyRequirement {
        doc /* The PCM shall bound ACC acceleration requests to its own ACC envelope, honour CANCEL_REQ, and produce coasting without a deceleration step on the inactive value. (External measure.) */
        :>> workProduct = "WP-S-02";
        :>> allocText = "EXT";
        :>> asil = "ext";
        :>> mechanism = "EXTM";
        :>> timing = "—";
        :>> verifMethod = "T-VEH";
    }
    requirement <'TSR-301'> tsr_301 : TechnicalSafetyRequirement {
        doc /* The envelope shall grant actuation authority only on the rising edge of PCM_CRUISE (0x1D2) CRUISE_ACTIVE, and only once the SoC heartbeat reports the item engaged within 1 s of that edge (otherwise not until the next rising edge), and shall revoke it in the same frame in which CRUISE_ACTIVE is received false (cancel, main switch off, PCM-internal drop). */
        :>> workProduct = "WP-S-02";
        :>> allocText = "P-SW";
        :>> asil = "C";
        :>> mechanism = "GATE";
        :>> timing = "detect ≤ 1 period (30 ms at 33 Hz) / same frame";
        :>> verifMethod = "T-SIL, T-VEH";
    }
    requirement <'TSR-302'> tsr_302 : TechnicalSafetyRequirement {
        doc /* The envelope shall revoke all actuation authority when a driver brake press is received (rising edge, or pressed while the vehicle is moving). */
        :>> workProduct = "WP-S-02";
        :>> allocText = "P-SW";
        :>> asil = "B";
        :>> mechanism = "GATE";
        :>> timing = "detect ≤ 1 period (25 ms at 40 Hz) / same frame; SS-L via TSR-109";
        :>> verifMethod = "T-SIL, T-VEH";
    }
    requirement <'TSR-303'> tsr_303 : TechnicalSafetyRequirement {
        doc /* On every fault-induced disengagement, with or without openpilot longitudinal, the SoC shall set CANCEL_REQ so that the PCM drops ACC. The PCM cruise state then changes, which changes the cluster cruise indication (TSR-309, AOU-12) and makes the envelope revoke (TSR-301); a cancel without effect is caught by TSR-516(c). */
        :>> workProduct = "WP-S-02";
        :>> allocText = "SoC";
        :>> asil = "QM (C-sup: TSR-203, TSR-301, TSR-516)";
        :>> mechanism = "FR";
        :>> timing = "≤ 0.1 s after disengagement";
        :>> verifMethod = "T-SIL, T-VEH";
    }
    requirement <'TSR-304'> tsr_304 : TechnicalSafetyRequirement {
        doc /* The envelope shall monitor STEER_TORQUE_DRIVER (0x260) on the LKA path and (a) reject 0x2E4 frames that increase torque opposing the driver beyond a driver allowance (driver-limited check in addition to the measured-torque check of TSR-104), and (b) when the driver torque exceeds T_ovr for longer than t_ovr, back off: accept only frames whose torque does not oppose the driver more than the previous frame, so that the commanded torque falls toward zero at no less than the Δ_down rate and stays there while the override lasts, and report the override state to the SoC (TSR-628). Lateral authority is kept, so assistance resumes when the driver releases (decided 2026-10-14, DQ-053: back off on override and show a cue; WP-A-05 LS-01, LS-02). T_ovr, t_ovr and the allowance shall be derived from the override behaviour accepted in WP-C-08 (assurance/02-concept/WP-C-08-driver-hmi-misuse-analysis.md) and from the EPS override threshold (AOU-02R). */
        :>> workProduct = "WP-S-02";
        :>> allocText = "P-SW";
        :>> asil = "B (SG-05); B‡ (SG-01, HE-05.2)";
        :>> mechanism = "PLB, GATE";
        :>> timing = "detect ≤ 2 frames of 0x260 (40 ms) + t_ovr, with t_ovr ≤ 0.1 s / torque decreasing the next frame, so the back-off starts ≤ 0.2 s after the driver's input (SG-05, WP-S-04 §3.7; SFM-ACT-016)";
        :>> verifMethod = "T-SIL, T-VEH";
    }
    requirement <'TSR-305'> tsr_305 : TechnicalSafetyRequirement {
        doc /* While the accelerator is pressed (PCM_CRUISE GAS_RELEASED = 0), the envelope shall withdraw longitudinal authority (inactive value only, TSR-203). The accelerator shall not revoke lateral authority in the reference configuration unless the HMI decision in WP-C-08 changes DisengageOnAccelerator. */
        :>> workProduct = "WP-S-02";
        :>> allocText = "P-SW";
        :>> asil = "B";
        :>> mechanism = "GATE";
        :>> timing = "detect ≤ 1 period / same frame";
        :>> verifMethod = "T-SIL";
    }
    requirement <'TSR-306'> tsr_306 : TechnicalSafetyRequirement {
        doc /* The envelope shall not grant actuation authority while any RX check of TSR-401…405 is failed, including timeouts not yet evaluated by the periodic check. */
        :>> workProduct = "WP-S-02";
        :>> allocText = "P-SW";
        :>> asil = "C";
        :>> mechanism = "GATE";
        :>> timing = "per frame";
        :>> verifMethod = "T-SIL";
    }
    requirement <'TSR-307'> tsr_307 : TechnicalSafetyRequirement {
        doc /* (a) The envelope shall revoke authority when the SoC heartbeat has reported "not engaged" continuously for 0.3 s while authority is granted; an "engaged" heartbeat restarts the count. (b) The SoC shall immediately disable when the envelope's reported authority differs from its own engaged state for > 0.3 s. */
        :>> workProduct = "WP-S-02";
        :>> allocText = "P-SW (a); SoC (b)";
        :>> asil = "(a) C; (b) QM (C-sup)";
        :>> mechanism = "PLB";
        :>> timing = "(a) ≤ 0.3 s / same tick; (b) ≤ 0.3 s";
        :>> verifMethod = "T-HIL, FI";
    }
    requirement <'TSR-308'> tsr_308 : TechnicalSafetyRequirement {
        doc /* If PCM cruise is active while the item is not engaged, or the item is engaged while PCM cruise is inactive, for longer than 1 s, the SoC shall warn the driver and request ACC cancel. */
        :>> workProduct = "WP-S-02";
        :>> allocText = "SoC";
        :>> asil = "QM (C-sup: TSR-301)";
        :>> mechanism = "PLB, WRN";
        :>> timing = "≤ 1 s";
        :>> verifMethod = "T-SIL";
    }
    requirement <'TSR-309'> tsr_309 : TechnicalSafetyRequirement {
        doc /* The engagement state enforced by the envelope shall be the PCM cruise state, so that the vehicle's cluster cruise indicator is an indication of engagement independent of the item's HMI. */
        :>> workProduct = "WP-S-02";
        :>> allocText = "P-SW, EXT";
        :>> asil = "C";
        :>> mechanism = "DES";
        :>> timing = "—";
        :>> verifMethod = "A, T-VEH";
    }
    requirement <'TSR-310'> tsr_310 : TechnicalSafetyRequirement {
        doc /* Driver brake application shall produce braking regardless of 0x343 content, and the PCM shall drop ACC on brake. (External measure.) */
        :>> workProduct = "WP-S-02";
        :>> allocText = "EXT";
        :>> asil = "ext";
        :>> mechanism = "EXTM";
        :>> timing = "—";
        :>> verifMethod = "T-VEH";
    }
    requirement <'TSR-311'> tsr_311 : TechnicalSafetyRequirement {
        doc /* Actuation authority shall be false at MCU start-up and after every safety-mode change, and all limiter state (last torque, rate windows, samples) shall be reset. */
        :>> workProduct = "WP-S-02";
        :>> allocText = "P-SW";
        :>> asil = "C";
        :>> mechanism = "GATE";
        :>> timing = "—";
        :>> verifMethod = "T-SIL";
    }
    requirement <'TSR-401'> tsr_401 : TechnicalSafetyRequirement {
        doc /* For each RX message used for gating or limiting (0xAA, 0x260, 0x1D2, 0x226, and 0x262, 0x1D3, 0xB4 once added), the envelope shall detect absence longer than 5 nominal periods and shall evaluate this at ≥ 50 Hz, so that worst-case detection is ≤ 0.2 s. */
        :>> workProduct = "WP-S-02";
        :>> allocText = "P-SW";
        :>> asil = "C";
        :>> mechanism = "TMO";
        :>> timing = "detect ≤ 0.2 s / react ≤ 0.1 s";
        :>> verifMethod = "T-SIL, T-HIL, FI";
    }
    requirement <'TSR-402'> tsr_402 : TechnicalSafetyRequirement {
        doc /* The envelope shall verify the Toyota checksum and the message length of every RX message that carries a checksum (0x260, 0x1D2, and 0x262, 0x1D3, 0xB4 once added) and treat one failed frame as an RX fault. */
        :>> workProduct = "WP-S-02";
        :>> allocText = "P-SW";
        :>> asil = "C";
        :>> mechanism = "E2E";
        :>> timing = "per frame";
        :>> verifMethod = "T-SIL";
    }
    requirement <'TSR-403'> tsr_403 : TechnicalSafetyRequirement {
        doc /* The envelope shall detect when an RX message arrives at more than 1.5× its nominal rate over a 100 ms window (indicating duplicated or inserted frames) and treat it as an RX fault. */
        :>> workProduct = "WP-S-02";
        :>> allocText = "P-SW";
        :>> asil = "C";
        :>> mechanism = "PLB";
        :>> timing = "detect ≤ 0.1 s";
        :>> verifMethod = "T-SIL, FI";
    }
    requirement <'TSR-404'> tsr_404 : TechnicalSafetyRequirement {
        doc /* For RX signals that vary in normal operation, the envelope shall detect a frozen payload: an identical data field (excluding checksum) for longer than t_frz while the vehicle is moving (0x260 torque/angle bytes; 0xAA wheel speeds above a minimum speed; 0xB4 ENCODER). t_frz shall be set from fork-owned drive logs so that no false detection occurs in the reference log set. */
        :>> workProduct = "WP-S-02";
        :>> allocText = "P-SW";
        :>> asil = "C";
        :>> mechanism = "PLB";
        :>> timing = "detect ≤ t_frz (target ≤ 0.2 s)";
        :>> verifMethod = "LOG, T-SIL, FI";
    }
    requirement <'TSR-405'> tsr_405 : TechnicalSafetyRequirement {
        doc /* The envelope shall apply these cross-checks and treat a disagreement lasting longer than its tolerance time as an RX fault: (a) wheel-speed mean (0xAA) vs SPEED (0xB4) within 2 m/s; (b) BRAKE_PRESSED in 0x226 vs PCM_CRUISE_2 (0x1D3) BRAKE_PRESSED — on disagreement the envelope shall assume "brake pressed" (revoke); (c) CRUISE_ACTIVE = 1 shall imply PCM_CRUISE_2 MAIN_ON = 1; (d) while authority is granted, measured EPS torque shall follow the accepted command within an EPS-response tolerance (detects frozen or replaced 0x260). Signal availability and tolerances shall be confirmed on reference-vehicle logs. */
        :>> workProduct = "WP-S-02";
        :>> allocText = "P-SW";
        :>> asil = "C";
        :>> mechanism = "PLB (cross-channel)";
        :>> timing = "detect ≤ 0.2 s";
        :>> verifMethod = "LOG, T-SIL, FI";
    }
    requirement <'TSR-406'> tsr_406 : TechnicalSafetyRequirement {
        doc /* On any RX fault of TSR-401…405, the envelope shall revoke all actuation authority within ≤ 0.1 s (SS-L via TSR-109, SS-G), report a fault-specific reason code to the SoC, and not grant authority again until all checks pass and a new PCM rising edge occurs. */
        :>> workProduct = "WP-S-02";
        :>> allocText = "P-SW";
        :>> asil = "C";
        :>> mechanism = "FR";
        :>> timing = "react ≤ 0.1 s";
        :>> verifMethod = "T-SIL, FI";
    }
    requirement <'TSR-407'> tsr_407 : TechnicalSafetyRequirement {
        doc /* In a car safety mode, the envelope shall detect absence of the SoC heartbeat (0xf3) for > 0.3 s and then revoke all actuation authority at once (SS-L, SS-G). It shall enter SS-S (SILENT, relay released) after the longer timeout of TSR-510. */
        :>> workProduct = "WP-S-02";
        :>> allocText = "P-SW";
        :>> asil = "C";
        :>> mechanism = "TMO";
        :>> timing = "detect ≤ 0.3 s / react ≤ 0.1 s";
        :>> verifMethod = "T-HIL, FI";
    }
    requirement <'TSR-408'> tsr_408 : TechnicalSafetyRequirement {
        doc /* While lateral authority is granted, the envelope shall monitor the arrival of 0x2E4 frames from the SoC and, if no frame arrives for > 50 ms (5 frames), revoke authority and command SS-L (TSR-109). While longitudinal authority is granted, the same shall apply to 0x343 with a gap > 100 ms. */
        :>> workProduct = "WP-S-02";
        :>> allocText = "P-SW";
        :>> asil = "C";
        :>> mechanism = "TMO";
        :>> timing = "detect ≤ 50 / 100 ms / react ≤ 0.1 s";
        :>> verifMethod = "T-HIL, FI";
    }
    requirement <'TSR-409'> tsr_409 : TechnicalSafetyRequirement {
        doc /* The heartbeat shall carry evidence that the control loop is alive (e.g. the latest carControl frame counter), and the envelope shall treat a heartbeat whose evidence has not advanced for > 0.3 s as a missing heartbeat. */
        :>> workProduct = "WP-S-02";
        :>> allocText = "P-SW, SoC";
        :>> asil = "C (panda check); QM (SoC content)";
        :>> mechanism = "TMO";
        :>> timing = "≤ 0.3 s";
        :>> verifMethod = "T-HIL, FI";
    }
    requirement <'TSR-410'> tsr_410 : TechnicalSafetyRequirement {
        doc /* Every SPI transfer (header and data) shall be protected by a CRC whose residual error probability over the maximum transfer length meets the target set in WP-S-05 §4 (assurance/03-system/WP-S-05-hsi-specification.md) (CRC-32C over the header, with endpoint, lengths, sequence counter and control-frame index, and the data; selected 2026-11-01), and every CAN-TX transfer shall carry a sequence counter; the envelope shall discard transfers with a failed CRC or a repeated or out-of-order counter. The per-packet XOR may remain as an additional check. Before sending 0x2E4 or 0x343, the envelope shall also verify the frame's Toyota checksum and refuse the frame if it fails (WP-S-05 §12.7 P-3). */
        :>> workProduct = "WP-S-02";
        :>> allocText = "P-SW, SoC";
        :>> asil = "C";
        :>> mechanism = "E2E";
        :>> timing = "per transfer";
        :>> verifMethod = "A, T-HIL, FI";
    }
    requirement <'TSR-411'> tsr_411 : TechnicalSafetyRequirement {
        doc /* The envelope shall reject actuation frames whose transfer counter shows they are older than 2 control periods relative to the newest accepted transfer (freshness). */
        :>> workProduct = "WP-S-02";
        :>> allocText = "P-SW";
        :>> asil = "C";
        :>> mechanism = "E2E";
        :>> timing = "per transfer";
        :>> verifMethod = "T-HIL, FI";
    }
    requirement <'TSR-412'> tsr_412 : TechnicalSafetyRequirement {
        doc /* The envelope shall validate every length field received over SPI against its buffer size before starting a DMA transfer or copy, and every control-request parameter used as an array index against the array bounds; a violation shall be NACKed and counted as an SPI error. */
        :>> workProduct = "WP-S-02";
        :>> allocText = "P-SW";
        :>> asil = "C";
        :>> mechanism = "ISO, PLB";
        :>> timing = "per transfer";
        :>> verifMethod = "R, T-HIL, FI";
    }
    requirement <'TSR-413'> tsr_413 : TechnicalSafetyRequirement {
        doc /* If SPI errors (header/data checksum failures, NACKs) exceed a rate threshold while authority is granted, the envelope shall revoke authority and report. */
        :>> workProduct = "WP-S-02";
        :>> allocText = "P-SW";
        :>> asil = "C";
        :>> mechanism = "FR";
        :>> timing = "≤ 0.3 s";
        :>> verifMethod = "T-HIL, FI";
    }
    requirement <'TSR-501'> tsr_501 : TechnicalSafetyRequirement {
        doc /* The safety MCU shall be supervised by an independent hardware watchdog (IWDG1, LSI-clocked) that is started no later than the first time the harness relay is energised after a reset, by any path (safety-mode change or configuration/debug command), and then stays active until the next reset; that cannot be stopped by the SoC; that is serviced only after the periodic safety processing has completed; and that resets the MCU within ≤ 0.1 s of a stall (SG-07 FDTI, WP-S-04 (assurance/03-system/WP-S-04-timing-ftti-budget.md) §3.6; ≤ 0.2 s would meet SG-01 only). Rationale for the start condition (amended in v0.4): until the relay is first energised after a reset, the stock camera-to-vehicle path is intact and no actuation frame reaches the vehicle, so a stall cannot violate SG-01 or SG-07; an idle device keeps its power-save and stop modes. */
        :>> workProduct = "WP-S-02";
        :>> allocText = "P-HW (cfg), P-SW";
        :>> asil = "C";
        :>> mechanism = "WDG";
        :>> timing = "detect ≤ 0.1 s / reset → SS-S";
        :>> verifMethod = "R, T-HIL, FI";
    }
    requirement <'TSR-502'> tsr_502 : TechnicalSafetyRequirement {
        doc /* Every detected MCU fault (watchdog, interrupt-rate, register divergence, memory ECC, clock, supply, temperature, SPI/DMA, siren, relay) shall lead to SS-S within ≤ 0.1 s of detection. Faults shall be classified as latching until power cycle or as recoverable, by documented rationale. During and after any reset the outputs shall be in SS-S until a valid safety mode is set. */
        :>> workProduct = "WP-S-02";
        :>> allocText = "P-SW, P-HW";
        :>> asil = "C";
        :>> mechanism = "FR";
        :>> timing = "react ≤ 0.1 s";
        :>> verifMethod = "R, FI";
    }
    requirement <'TSR-503'> tsr_503 : TechnicalSafetyRequirement {
        doc /* Memory faults that can corrupt actuation decisions shall be detected: RAM ECC with double-error reaction, flash image CRC at start-up and periodically, and periodic check of safety-critical configuration registers, each leading to TSR-502. */
        :>> workProduct = "WP-S-02";
        :>> allocText = "P-HW (cfg), P-SW";
        :>> asil = "C";
        :>> mechanism = "ST, PLB";
        :>> timing = "≤ 0.2 s for RAM/register faults; flash: start-up + background";
        :>> verifMethod = "R, FI";
    }
    requirement <'TSR-504'> tsr_504 : TechnicalSafetyRequirement {
        doc /* Loss or drift of the MCU clock that would invalidate timing checks or CAN bit timing shall be detected and lead to TSR-502. */
        :>> workProduct = "WP-S-02";
        :>> allocText = "P-HW (cfg), P-SW";
        :>> asil = "C";
        :>> mechanism = "PLB";
        :>> timing = "≤ 0.2 s";
        :>> verifMethod = "FI";
    }
    requirement <'TSR-505'> tsr_505 : TechnicalSafetyRequirement {
        doc /* Supply voltage of the MCU outside its operating range shall lead to reset or SS-S (brown-out reset, programmable voltage detector), and vehicle input voltage out of range while the relay is driven shall lead to SS-S. */
        :>> workProduct = "WP-S-02";
        :>> allocText = "P-HW, P-SW";
        :>> asil = "C";
        :>> mechanism = "PLB";
        :>> timing = "≤ 0.2 s";
        :>> verifMethod = "T-HIL";
    }
    requirement <'TSR-506'> tsr_506 : TechnicalSafetyRequirement {
        doc /* The intercept relay shall be de-energise-to-safe, its actual state shall be read back and compared with the commanded state in both directions within ≤ 0.3 s, and a detected relay malfunction shall inhibit all actuation TX and be latched until power cycle (not cleared by a safety-mode change). */
        :>> workProduct = "WP-S-02";
        :>> allocText = "P-HW, HAR, P-SW";
        :>> asil = "C (blocking), B (PCS restore)";
        :>> mechanism = "PLB, FR";
        :>> timing = "detect ≤ 0.3 s";
        :>> verifMethod = "A, T-HIL, FI";
    }
    requirement <'TSR-507'> tsr_507 : TechnicalSafetyRequirement {
        doc /* Safety-critical data (safety mode and parameter, limits, authority state, relay state) and the stacks shall be protected against writes from communication handlers by the MPU, with a stack guard, and a MemManage fault shall lead to TSR-502. */
        :>> workProduct = "WP-S-02";
        :>> allocText = "P-HW (cfg), P-SW";
        :>> asil = "C";
        :>> mechanism = "ISO";
        :>> timing = "—";
        :>> verifMethod = "R, FI";
    }
    requirement <'TSR-508'> tsr_508 : TechnicalSafetyRequirement {
        doc /* The car-side CAN transceiver shall be non-transmitting from reset until enabled by firmware; bus-off or persistent TX failure on the car-side bus while authority is granted shall revoke authority and be reported. */
        :>> workProduct = "WP-S-02";
        :>> allocText = "P-HW, P-SW";
        :>> asil = "C";
        :>> mechanism = "FR";
        :>> timing = "≤ 0.3 s";
        :>> verifMethod = "T-HIL, FI";
    }
    requirement <'TSR-509'> tsr_509 : TechnicalSafetyRequirement {
        doc /* MCU die temperature outside its specified range shall lead to SS-S. */
        :>> workProduct = "WP-S-02";
        :>> allocText = "P-HW, P-SW";
        :>> asil = "C";
        :>> mechanism = "PLB";
        :>> timing = "≤ 1 s";
        :>> verifMethod = "T-HIL";
    }
    requirement <'TSR-510'> tsr_510 : TechnicalSafetyRequirement {
        doc /* Ignition state shall be sensed from the harness ignition line; loss of the SoC heartbeat shall lead to SS-S after ≤ 2 s regardless of the ignition reading, and a failed ignition input shall not keep the relay driven without a heartbeat. */
        :>> workProduct = "WP-S-02";
        :>> allocText = "P-HW, HAR, P-SW";
        :>> asil = "B";
        :>> mechanism = "TMO";
        :>> timing = "SS-S ≤ 2 s";
        :>> verifMethod = "A, T-HIL";
    }
    requirement <'TSR-511'> tsr_511 : TechnicalSafetyRequirement {
        doc /* Only release-signed LionDriver firmware shall execute on the safety MCU: the bootstub shall verify an ECDSA signature over P-256 with SHA-256 (decided 2026-10-19, DQ-191 A; replaces RSA-1024/SHA-1), flash read-out and write protection shall be set, the SoC's control of STM_BOOT0/STM_RST_N shall not allow non-release code to drive the relay, release builds of pandad shall not flash a development bootstub, and softloader entry (0xd1 param 1) shall be refused in a car safety mode and while the ignition is on (CSR-024). */
        :>> workProduct = "WP-S-02";
        :>> allocText = "P-SW, P-HW (option bytes), SoC";
        :>> asil = "C (+ CS)";
        :>> mechanism = "CFG";
        :>> timing = "—";
        :>> verifMethod = "R, T-HIL";
    }
    requirement <'TSR-512'> tsr_512 : TechnicalSafetyRequirement {
        doc /* In release builds for the reference configuration the safety MCU shall accept only the modes SILENT, NOOUTPUT, ELM327 (fingerprinting, relay released) and TOYOTA with the reference safety parameter compiled into the firmware (EPS factor 73, no flags). Once TOYOTA mode is active, it shall accept only a change to NOOUTPUT or SILENT; any other request shall be rejected and reported. The alternative-experience word shall likewise be fixed to the reference value in release builds, so that it cannot be changed in a non-car mode and carried into a later TOYOTA session. */
        :>> workProduct = "WP-S-02";
        :>> allocText = "P-SW";
        :>> asil = "C";
        :>> mechanism = "CFG";
        :>> timing = "per request";
        :>> verifMethod = "R, T-HIL";
    }
    requirement <'TSR-513'> tsr_513 : TechnicalSafetyRequirement {
        doc /* In release builds for the reference configuration, while a car safety mode is active, the safety MCU shall accept only the control requests the main computer sends while driving or when pandad restarts (WP-S-05 §4.2a, DQ-147 A): heartbeat, health, fan and IR power, comms reset, the debug-log read, the reconnect reads, a safety-mode change as TSR-512 restricts it and leaving power save. Every other request shall be rejected, including request codes added later. Requests that drive the relay, change the CAN bit rate, loopback or clock output, or disable the heartbeat check shall be rejected in every mode, so that a downgrade from TOYOTA cannot use them and no setting carries into the next TOYOTA session. Once TOYOTA has been active, softloader entry (0xd1 param 1, see also TSR-511) and OBD multiplexing shall stay rejected until the ignition is seen off. A refused request is ignored: it shall not change the actuation state, and it does not by itself end actuation authority (decided 2026-10-19, DQ-082 B; the alternative, withdrawing authority and reporting it as RR-2026-009 F-36 and CSR-012 propose, was not chosen, so CSR-012's intent stays an open item of the cybersecurity case, WP-S-07 (assurance/03-system/WP-S-07-cybersecurity-requirements-architecture.md)). */
        :>> workProduct = "WP-S-02";
        :>> allocText = "P-SW";
        :>> asil = "C";
        :>> mechanism = "CFG";
        :>> timing = "per request";
        :>> verifMethod = "R, T-HIL";
    }
    requirement <'TSR-514'> tsr_514 : TechnicalSafetyRequirement {
        doc /* Release firmware shall be built without ALLOW_DEBUG, with the LionDriver release key, and shall not contain the ALLOUTPUT mode, debug-only safety modes or debug-key acceptance; the build type shall be readable through the version request and recorded in the release record. */
        :>> workProduct = "WP-S-02";
        :>> allocText = "P-SW (build)";
        :>> asil = "C (+ CS)";
        :>> mechanism = "CFG";
        :>> timing = "—";
        :>> verifMethod = "R";
    }
    requirement <'TSR-515'> tsr_515 : TechnicalSafetyRequirement {
        doc /* At every power-up, before the relay is first driven, the safety MCU shall run start-up tests of its safety mechanisms (flash CRC, RAM test of safety data regions, watchdog reset path at a defined interval, relay drive and readback, siren path) and stay in SS-S and report if any test fails. */
        :>> workProduct = "WP-S-02";
        :>> allocText = "P-SW, P-HW";
        :>> asil = "C";
        :>> mechanism = "ST";
        :>> timing = "once per drive cycle";
        :>> verifMethod = "T-HIL, FI";
    }
    requirement <'TSR-516'> tsr_516 : TechnicalSafetyRequirement {
        doc /* The safety MCU shall sound its own acoustic warning within ≤ 0.5 s of detection (except as stated below for (b) on an EPS fault), without depending on SoC software, for at least 3 s or for as long as its condition holds if longer, at a level audible over the cabin noise of the reference vehicle (level set by WP-S-04 M-05), when (a) the SoC heartbeat is lost (TSR-407) while authority is granted; if authority ended within the 5 s before the loss, a warning within ≤ 5 s of the loss is sufficient, because the driver has already been told of the disengagement (decided 2026-10-14, DQ-061 A); (b) the envelope revokes authority while it is granted for any reason other than a driver action that the envelope itself observes (brake press, TSR-302; PCM cruise inactive, TSR-301), that is on missing SoC command frames (TSR-408), an RX fault (TSR-406), an EPS fault state (TSR-110), a rejected command (TSR-108), a car-side TX failure or bus-off (TSR-508) or a platform fault (TSR-502); or (c) PCM cruise is still active 0.5 s (within one 10 ms task period) after the SoC heartbeat first reported "not engaged" (a fault-induced disengagement whose ACC cancel, TSR-303, had no effect); or (d) the safety MCU restarts after a watchdog or fault reset (TSR-501, TSR-502) that interrupted granted authority. For (b) on an EPS fault, this clause replaces the ≤ 0.5 s bound: detection is the first fault frame, any persistence filter before the warning shall be ≤ 0.7 s, and the siren shall sound within the SG-02 1 s warning budget from fault onset (decided 2026-10-14, DQ-048). For (d), the item's engaged state shall be kept across the reset in memory that the reset does not clear, and the siren shall sound ≤ 0.5 s after the restart (decided 2026-10-14, DQ-054). A stalled SoC stops both the command frames and the heartbeat; whichever of TSR-408 and TSR-407 revokes first shall sound the siren under (b) or (a), so that a SoC stall is never silent, while a disengagement by the driver stays silent (decided 2026-10-19, DQ-404 A). A revocation on a heartbeat "not engaged" (TSR-307(a)) sounds the siren under (c), not (b): only if PCM cruise is still active 0.5 s after the first such heartbeat, so that a disengagement openpilot ends with an ACC cancel stays silent (cancel-lag guard, decided by the lead 2026-10-21; the PCM cancel lag is to be measured, WP-W-02 OI-18). */
        :>> workProduct = "WP-S-02";
        :>> allocText = "P-SW, P-HW";
        :>> asil = "C";
        :>> mechanism = "WRN";
        :>> timing = "≤ 0.5 s after detection";
        :>> verifMethod = "T-HIL";
    }
    requirement <'TSR-517'> tsr_517 : TechnicalSafetyRequirement {
        doc /* Corruption of an approved actuation frame after the TX hook (copy into FDCAN message RAM, message RAM, FDCAN core, transceiver) shall be detected, e.g. by reading back the safety MCU's own transmitted frames on the car-side bus and comparing them with the approved frame, and a mismatch shall lead to TSR-502. */
        :>> workProduct = "WP-S-02";
        :>> allocText = "P-SW, P-HW";
        :>> asil = "C";
        :>> mechanism = "PLB";
        :>> timing = "≤ 2 frames / react per TSR-502";
        :>> verifMethod = "A, FI";
    }
    requirement <'TSR-518'> tsr_518 : TechnicalSafetyRequirement {
        doc /* The envelope shall supervise the transmit rate of each actuation message ID (0x2E4, 0x343, 0x412, and any other TX-whitelisted ID) against its nominal period and reject frames sent faster than the nominal rate plus a defined tolerance; persistent excess while authority is granted shall revoke authority and be reported. */
        :>> workProduct = "WP-S-02";
        :>> allocText = "P-SW";
        :>> asil = "C";
        :>> mechanism = "TMO";
        :>> timing = "per frame; revoke ≤ 0.1 s after the first rejected frame (DN-01 (assurance/05-software/design-notes/DN-01-tx-rate-supervision.md) D-6; ≤ 0.2 s from the onset of a flood at 2× the nominal rate)";
        :>> verifMethod = "T-SIL, T-HIL";
    }
    requirement <'TSR-519'> tsr_519 : TechnicalSafetyRequirement {
        doc /* The safety MCU shall have a documented interrupt-priority and execution-timing scheme: priorities assigned explicitly for every enabled interrupt; safety hooks, CAN TX and SoC command dispatch either moved out of interrupt context or bounded by measured WCET; and the worst-case latency of the periodic safety processing (timeouts, heartbeat, watchdog service) shown to meet the TSR-401/407/501 budgets under worst-case interrupt load. */
        :>> workProduct = "WP-S-02";
        :>> allocText = "P-SW, P-HW (cfg)";
        :>> asil = "C";
        :>> mechanism = "ISO";
        :>> timing = "analysis; WCET measured on target";
        :>> verifMethod = "A, T-HIL";
    }
    requirement <'TSR-601'> tsr_601 : TechnicalSafetyRequirement {
        doc /* selfdrived shall classify faults as (i) untrusted command or input (loss or staleness of an input to the control law, model failure, CAN error, controls mismatch) → immediate disable, and (ii) trustworthy but degrading (thermal, storage, memory) → soft disable. Actuation on an input that has failed its alive or validity check shall end within ≤ 0.2 s. */
        :>> workProduct = "WP-S-02";
        :>> allocText = "SoC";
        :>> asil = "QM (C-sup: TSR-407, TSR-408)";
        :>> mechanism = "FR";
        :>> timing = "≤ 0.2 s";
        :>> verifMethod = "T-SIL, FI";
    }
    requirement <'TSR-602'> tsr_602 : TechnicalSafetyRequirement {
        doc /* controlsd shall check the age of modelV2, longitudinalPlan and carState before use (≤ 2 nominal periods) and shall set latActive/longActive false and raise an event when an input is stale. */
        :>> workProduct = "WP-S-02";
        :>> allocText = "SoC";
        :>> asil = "QM (C-sup: TSR-408)";
        :>> mechanism = "TMO";
        :>> timing = "≤ 0.1 s";
        :>> verifMethod = "T-SIL";
    }
    requirement <'TSR-603'> tsr_603 : TechnicalSafetyRequirement {
        doc /* No diagnostic (commIssue, posenet, locationd, modeldLagging) shall be masked while the item is engaged, and the driving model shall not be switched while engaged. In the reference configuration the external big model (E-06) shall be absent and not loadable. */
        :>> workProduct = "WP-S-02";
        :>> allocText = "SoC";
        :>> asil = "QM (C-sup)";
        :>> mechanism = "DES";
        :>> timing = "—";
        :>> verifMethod = "R, T-SIL";
    }
    requirement <'TSR-604'> tsr_604 : TechnicalSafetyRequirement {
        doc /* Non-finite actuator commands shall be treated as a fault with immediate disable, not replaced silently. */
        :>> workProduct = "WP-S-02";
        :>> allocText = "SoC";
        :>> asil = "QM (C-sup)";
        :>> mechanism = "FR";
        :>> timing = "≤ 1 frame";
        :>> verifMethod = "T-SIL";
    }
    requirement <'TSR-605'> tsr_605 : TechnicalSafetyRequirement {
        doc /* The SoC controller shall command with margin below every envelope limit: steering torque ≤ 90 % of τ_max(v), acceleration within [a_min + 0.2, a_max − 0.2] m/s² (proposed), lateral acceleration ≤ 3.0 m/s², lateral jerk ≤ 5 m/s³. */
        :>> workProduct = "WP-S-02";
        :>> allocText = "SoC";
        :>> asil = "QM";
        :>> mechanism = "LIM";
        :>> timing = "per frame";
        :>> verifMethod = "T-SIL";
    }
    requirement <'TSR-606'> tsr_606 : TechnicalSafetyRequirement {
        doc /* On every fault-induced transition to L2/L3 (FSC §12) the SoC shall give a visual and acoustic take-over request within ≤ 1 s of detection, with text that names the actual fault class. */
        :>> workProduct = "WP-S-02";
        :>> allocText = "SoC (HMI)";
        :>> asil = "QM (C-sup: TSR-516)";
        :>> mechanism = "WRN";
        :>> timing = "≤ 1 s";
        :>> verifMethod = "T-HIL, T-VEH";
    }
    requirement <'TSR-607'> tsr_607 : TechnicalSafetyRequirement {
        doc /* The SoC shall warn the driver when the EPS reports LKA unavailable or faulted (complements TSR-110). (a) Outside the cases of (b) the warning is the take-over request (soft disable, visual and acoustic). (b) When the fault starts within 1.5 s of a driver steering override, or at standstill, the SoC may first give the lighter prompt (small alert with chime); if the fault is still present 1.5 s after it started, the SoC shall escalate to the take-over request of (a). The lighter prompt shall not be held for the duration of the fault. (Decided 2026-10-16, register DQ-342, A; System FMEA SFM-ACT-023.) (c) When the fault starts while the driver is steering and lasts more than 1.5 s while they keep steering, the SoC shall give at least the lighter prompt, so that the driver learns of the lost assistance before releasing the wheel; on release the take-over request of (a) follows at once. (Decided by the lead in chat on 2026-10-17, register DQ-366, A; impact record OI-2.) */
        :>> workProduct = "WP-S-02";
        :>> allocText = "SoC";
        :>> asil = "QM (C-sup: TSR-110)";
        :>> mechanism = "WRN";
        :>> timing = "(a) ≤ 1 s; (b) prompt ≤ 1 s, take-over request ≤ 1.5 s after fault onset (the driver has hands on the wheel within the window)";
        :>> verifMethod = "T-SIL, T-VEH";
    }
    requirement <'TSR-608'> tsr_608 : TechnicalSafetyRequirement {
        doc /* Driver monitoring shall escalate warnings for an inattentive driver with the timing set in WP-C-08 §5 (baseline vision 5/8/13 s, wheel-touch 5/15/25 s). */
        :>> workProduct = "WP-S-02";
        :>> allocText = "SoC";
        :>> asil = "A (SG-08; allocated to the QM SoC, open: WP-C-04 OI-11)";
        :>> mechanism = "WRN";
        :>> timing = "per policy";
        :>> verifMethod = "T-SIL, T-VEH";
    }
    requirement <'TSR-609'> tsr_609 : TechnicalSafetyRequirement {
        doc /* The DM chain shall mark its output invalid when the cabin image or model output is missing or not credible, and an invalid DM output for > 2 s while engaged shall escalate to a take-over request. */
        :>> workProduct = "WP-S-02";
        :>> allocText = "SoC";
        :>> asil = "A (SG-08; allocated to the QM SoC, open: WP-C-04 OI-11)";
        :>> mechanism = "PLB";
        :>> timing = "≤ 2 s";
        :>> verifMethod = "T-SIL, FI";
    }
    requirement <'TSR-610'> tsr_610 : TechnicalSafetyRequirement {
        doc /* DM demo mode (IsDriverViewEnabled) shall not be active while the item can engage. */
        :>> workProduct = "WP-S-02";
        :>> allocText = "SoC";
        :>> asil = "A (SG-08; allocated to the QM SoC, open: WP-C-04 OI-11)";
        :>> mechanism = "CFG";
        :>> timing = "—";
        :>> verifMethod = "R, T-SIL";
    }
    requirement <'TSR-611'> tsr_611 : TechnicalSafetyRequirement {
        doc /* If the driver does not respond to the highest DM warning, the SoC shall decelerate, disengage and lock out re-engagement for 1/5/15/30 min. */
        :>> workProduct = "WP-S-02";
        :>> allocText = "SoC";
        :>> asil = "A (SG-08; allocated to the QM SoC, open: WP-C-04 OI-11)";
        :>> mechanism = "FR";
        :>> timing = "per policy";
        :>> verifMethod = "T-SIL, T-VEH";
    }
    requirement <'TSR-612'> tsr_612 : TechnicalSafetyRequirement {
        doc /* The wheel-touch fallback shall reset awareness only on a deliberate driver input above a defined threshold, not on any steering or gas input. */
        :>> workProduct = "WP-S-02";
        :>> allocText = "SoC";
        :>> asil = "A (SG-08; allocated to the QM SoC, open: WP-C-04 OI-11)";
        :>> mechanism = "PLB";
        :>> timing = "—";
        :>> verifMethod = "T-SIL";
    }
    requirement <'TSR-613'> tsr_613 : TechnicalSafetyRequirement {
        doc /* Debug, joystick and maneuver modes, and the lateralManeuverPlan path to the actuator, shall be absent from reference-configuration builds. */
        :>> workProduct = "WP-S-02";
        :>> allocText = "SoC";
        :>> asil = "QM (C-sup); A where it keeps DM active (FSR-02.08, WP-C-04 OI-11)";
        :>> mechanism = "CFG";
        :>> timing = "—";
        :>> verifMethod = "R";
    }
    requirement <'TSR-614'> tsr_614 : TechnicalSafetyRequirement {
        doc /* pandad shall not forward sendcan messages older than 2 control periods (20 ms). */
        :>> workProduct = "WP-S-02";
        :>> allocText = "SoC";
        :>> asil = "QM (C-sup: TSR-411)";
        :>> mechanism = "TMO";
        :>> timing = "20 ms";
        :>> verifMethod = "T-SIL";
    }
    requirement <'TSR-615'> tsr_615 : TechnicalSafetyRequirement {
        doc /* The SoC shall immediately disable on any panda fault flag, heartbeat-lost flag, rising safetyTxBlocked count while engaged, or SPI error burst reported in pandaStates. */
        :>> workProduct = "WP-S-02";
        :>> allocText = "SoC";
        :>> asil = "QM (C-sup: TSR-502, TSR-108)";
        :>> mechanism = "FR";
        :>> timing = "≤ 0.2 s";
        :>> verifMethod = "T-SIL, FI";
    }
    requirement <'TSR-616'> tsr_616 : TechnicalSafetyRequirement {
        doc /* Driving-model outputs shall be checked for non-finite values, range plausibility and age before use, per AIR-16, AIR-17 and AIR-25 of WP-C-11 (assurance/02-concept/WP-C-11-ai-system-definition-and-safety-requirements.md). */
        :>> workProduct = "WP-S-02";
        :>> allocText = "SoC";
        :>> asil = "QM";
        :>> mechanism = "PLB";
        :>> timing = "per frame";
        :>> verifMethod = "T-SIL";
    }
    requirement <'TSR-617'> tsr_617 : TechnicalSafetyRequirement {
        doc /* Excessive-actuation detection (longitudinal outside 2× ACCEL_MIN/MAX, lateral > 2× ISO lateral acceleration for > 0.25 s) shall be kept and shall latch until cleared offroad. */
        :>> workProduct = "WP-S-02";
        :>> allocText = "SoC";
        :>> asil = "QM";
        :>> mechanism = "PLB";
        :>> timing = "0.25 s";
        :>> verifMethod = "T-SIL";
    }
    requirement <'TSR-618'> tsr_618 : TechnicalSafetyRequirement {
        doc /* A PCM-reported ACC fault shall cause immediate disable with a take-over request. */
        :>> workProduct = "WP-S-02";
        :>> allocText = "SoC";
        :>> asil = "QM (C-sup)";
        :>> mechanism = "FR";
        :>> timing = "≤ 0.2 s";
        :>> verifMethod = "T-SIL";
    }
    requirement <'TSR-619'> tsr_619 : TechnicalSafetyRequirement {
        doc /* pandad shall compare the panda-reported safety model, safety parameter and alternative experience with the release-record values and shall prevent engagement and raise an alert on mismatch (refines CSR-016 of WP-S-07 (assurance/03-system/WP-S-07-cybersecurity-requirements-architecture.md)). */
        :>> workProduct = "WP-S-02";
        :>> allocText = "SoC";
        :>> asil = "QM (C-sup: TSR-512)";
        :>> mechanism = "PLB";
        :>> timing = "before engagement; ≤ 1 s";
        :>> verifMethod = "T-SIL, T-HIL";
    }
    requirement <'TSR-620'> tsr_620 : TechnicalSafetyRequirement {
        doc /* The item shall not request the TOYOTA safety mode or allow engagement unless the ECU firmware versions read at start-up (EPS, engine, ABS, radar, camera) match the release record of the reference configuration; an unverified or mismatching firmware set shall keep the safety MCU in NOOUTPUT and inform the driver. The envelope cannot read ECU firmware itself, so the refusal rests on the SoC query plus the mode lock of TSR-512. */
        :>> workProduct = "WP-S-02";
        :>> allocText = "SoC";
        :>> asil = "QM (C-sup: TSR-512, TSR-803)";
        :>> mechanism = "CFG";
        :>> timing = "at start-up";
        :>> verifMethod = "T-SIL, T-VEH";
    }
    requirement <'TSR-621'> tsr_621 : TechnicalSafetyRequirement {
        doc /* While engaged, selfdrived shall raise an immediate disable with a take-over request when any panda in a car safety mode reports controlsAllowed false, after at most 2 consecutive mismatched samples to absorb transport skew between the CAN and pandaStates sockets, and in any case within ≤ 0.5 s of the first mismatched sample. */
        :>> workProduct = "WP-S-02";
        :>> allocText = "SoC";
        :>> asil = "QM (C-sup: TSR-108, TSR-516)";
        :>> mechanism = "PLB";
        :>> timing = "≤ 0.5 s / ≤ 0.5 s to warning";
        :>> verifMethod = "T-SIL, FI";
    }
    requirement <'TSR-622'> tsr_622 : TechnicalSafetyRequirement {
        doc /* While the item can engage, the SoC shall supervise the liveness of the HMI path (UI render loop and sound output stream, each with a heartbeat) and treat a missing heartbeat for > 1 s as a fault: immediate disable, with the take-over request carried by the panda siren (TSR-516) and the cluster cruise state (TSR-309, FSR-05.05). */
        :>> workProduct = "WP-S-02";
        :>> allocText = "SoC (HMI)";
        :>> asil = "QM (C-sup: TSR-516)";
        :>> mechanism = "TMO";
        :>> timing = "≤ 1 s / ≤ 0.2 s";
        :>> verifMethod = "T-SIL, FI";
    }
    requirement <'TSR-623'> tsr_623 : TechnicalSafetyRequirement {
        doc /* Alert sound output shall not be muted or set below a defined audible minimum while the item can engage; if the minimum cannot be guaranteed, engagement shall be prevented with a no-entry alert. */
        :>> workProduct = "WP-S-02";
        :>> allocText = "SoC (HMI)";
        :>> asil = "QM (C-sup: TSR-516)";
        :>> mechanism = "CFG";
        :>> timing = "—";
        :>> verifMethod = "R, T-SIL";
    }
    requirement <'TSR-624'> tsr_624 : TechnicalSafetyRequirement {
        doc /* The SoC shall command deceleration that is not caused by traffic (driver-monitoring no-response, fault-induced force deceleration) only after a visual and acoustic alert announcing it has been given, and shall ramp the request within the envelope bounds a_min (TSR-202) and j_down (TSR-205). The 1 s lead time applies to the driver-monitoring no-response deceleration; a fault soft-disable deceleration may start on the first frame of its alert (DQ-407 A). Rationale: that slow-down is gentle (at most −1.2 m/s² over the 3 s before control is handed back, about 13 km/h at most), its alert sounds from the first frame, and holding it back 1 s means driving on at speed with the fault still active; the plant search found no contact in any order of alert and slow-down (synthetic, no credit). */
        :>> workProduct = "WP-S-02";
        :>> allocText = "SoC";
        :>> asil = "QM (B-sup: TSR-202, TSR-205)";
        :>> mechanism = "WRN";
        :>> timing = "Driver-monitoring stop: alert ≥ 1 s before decel onset (proposed); fault soft disable: alert from the first frame of the decel (DQ-407 A)";
        :>> verifMethod = "T-SIL, T-VEH";
    }
    requirement <'TSR-625'> tsr_625 : TechnicalSafetyRequirement {
        doc /* Forward collision warnings shall be raised only from fresh and valid inputs (modelV2 and longitudinalPlan within 2 nominal periods, validity flags set), and the false-FCW rate per driving hour in the ODD shall meet a target set in WP-V-02 (assurance/06-validation/WP-V-02-sotif-vv-strategy.md). */
        :>> workProduct = "WP-S-02";
        :>> allocText = "SoC";
        :>> asil = "A (until re-rated: DQ-052 A, WP-C-04 OI-9; allocated to the QM SoC)";
        :>> mechanism = "PLB";
        :>> timing = "≤ 2 periods";
        :>> verifMethod = "T-SIL, LOG";
    }
    requirement <'TSR-626'> tsr_626 : TechnicalSafetyRequirement {
        doc /* While engaged, the SoC shall detect that the envelope does not actuate from evidence other than the envelope's own status report: (a) pandaStates older than 2 nominal periods (0.2 s) is treated as a controls mismatch (TSR-621); (b) with lateral control active, the EPS-applied torque (STEER_TORQUE_EPS in 0x260) not following a commanded torque above a threshold for longer than t_blk; (c) with longitudinal control active, the measured acceleration not following the requested acceleration beyond a tolerance for longer than t_blk. (d) with lateral control active, EPS_STATUS (0x262) LKA_STATE not reporting LKA active, or with longitudinal control active, the PCM not reporting ACC in control, for longer than t_blk; (e) the transmitted-frame count of TSR-632 not advancing for a commanded actuation ID. Each leads to immediate disable with a take-over request, so that the warning falls within the SG-02/SG-06 1 s budget (SFM-ACT-018). Threshold, tolerance and t_blk (≤ 0.5 s) shall be set from fork-owned drive logs so that no false detection occurs in the reference log set. (b) and (c) target envelope blocking; an EPS or PCM that silently stops acting on the item's requests is covered by AOU-17 instead, verified with forced faults (decided 2026-10-18, DQ-360 A); if that test finds a silent drop, (b) and (c) are extended to it. */
        :>> workProduct = "WP-S-02";
        :>> allocText = "SoC";
        :>> asil = "QM (C-sup: TSR-516)";
        :>> mechanism = "PLB";
        :>> timing = "(a) 0.2 s; (b), (c) ≤ t_blk ≤ 0.5 s";
        :>> verifMethod = "LOG, T-SIL, FI";
    }
    requirement <'TSR-627'> tsr_627 : TechnicalSafetyRequirement {
        doc /* The alert sound path (soundd) shall run with a real-time scheduling priority not lower than that of ui, or a worst-case load test (maximum logging, encoding and upload) shall show that alert sound output starts within the TSR-606 budget. */
        :>> workProduct = "WP-S-02";
        :>> allocText = "SoC (HMI)";
        :>> asil = "QM (C-sup: TSR-516)";
        :>> mechanism = "TMO";
        :>> timing = "within TSR-606";
        :>> verifMethod = "T-SIL (load), T-HIL";
    }
    requirement <'TSR-628'> tsr_628 : TechnicalSafetyRequirement {
        doc /* While the envelope reports a driver override on the LKA path (TSR-304(b)), the SoC shall show an override cue on the device display within ≤ 0.2 s, so the driver sees that the steering backed off and why. */
        :>> workProduct = "WP-S-02";
        :>> allocText = "SoC";
        :>> asil = "QM";
        :>> mechanism = "WRN";
        :>> timing = "≤ 0.2 s";
        :>> verifMethod = "T-SIL, T-VEH";
    }
    requirement <'TSR-629'> tsr_629 : TechnicalSafetyRequirement {
        doc /* At start-up, before the first engagement of each ignition cycle, the SoC shall read the stored diagnostic trouble codes (DTCs) of the EPS and of the brake / stability control (ABS/VSC) ECU, and shall prevent engagement with a no-entry alert naming the system while either ECU reports an active code. (a) The read shall run only while the item cannot be engaged (before the car safety mode is requested) and only after the vehicle has been seen stationary; it shall never run while the vehicle moves or the item is engaged. (b) A code is active when its status shows test failed, test failed this operation cycle, confirmed, or warning indicator requested (ISO 14229-1 status bits 0, 1, 3, 7), counting only the bits the ECU reports as supported. Pending or history bits alone do not count. A code the release record exempts as not affecting lateral or longitudinal control does not count; none is exempt in the first release, and an exemption needs an impact analysis. (c) A read that was not made (vehicle not seen stationary), not answered completely within the read time, answered with a negative response or malformed, or that reports none of the active bits as supported, shall also prevent engagement, with its own no-entry alert, until the next start-up. (d) The result is an entry condition only: it does not disengage an engaged item. The driver's lamp check (WP-O-02 OPS-01) stays as a second barrier. */
        :>> workProduct = "WP-S-02";
        :>> allocText = "SoC";
        :>> asil = "QM (supports TSR-110, TSR-618)";
        :>> mechanism = "PLB, ST";
        :>> timing = "before engagement";
        :>> verifMethod = "T-SIL, T-VEH";
    }
    requirement <'TSR-630'> tsr_630 : TechnicalSafetyRequirement {
        doc /* While a car safety mode is active and the item is not engaged, the SoC shall check that every panda reports controlsAllowed false. A report of true for more than 2 consecutive pandaStates samples, and in any case within ≤ 0.3 s, shall prevent engagement with a no-entry alert, be logged as an envelope fault, and request ACC cancel. (The reverse of TSR-621: it makes a latent panda authority fault visible before the host also commands torque.) */
        :>> workProduct = "WP-S-02";
        :>> allocText = "SoC";
        :>> asil = "QM (C-sup: TSR-105, TSR-301)";
        :>> mechanism = "PLB";
        :>> timing = "≤ 0.3 s (within the SG-01 0.5 s FTTI)";
        :>> verifMethod = "T-SIL, FI";
    }
    requirement <'TSR-631'> tsr_631 : TechnicalSafetyRequirement {
        doc /* controlsd shall treat the driving-model output as stale, with the TSR-602 reaction, when (a) its frame ID does not advance for more than 2 nominal periods while messages keep arriving (frozen output), or (b) its age measured from the source camera frame timestamp, not the publish time, exceeds 2 nominal periods (stale content with fresh timestamps). */
        :>> workProduct = "WP-S-02";
        :>> allocText = "SoC";
        :>> asil = "QM (C-sup: TSR-101, TSR-103 bound the effect; TSR-408 covers a stopped command stream)";
        :>> mechanism = "TMO, PLB";
        :>> timing = "≤ 0.1 s";
        :>> verifMethod = "T-SIL, FI";
    }
    requirement <'TSR-632'> tsr_632 : TechnicalSafetyRequirement {
        doc /* The safety MCU shall report to the SoC, for each supervised actuation ID (0x2E4, 0x343), the count of frames accepted by the envelope and transmitted on the car-side bus (transmit complete) and the count refused, in every health report. */
        :>> workProduct = "WP-S-02";
        :>> allocText = "P-SW";
        :>> asil = "C (report content); QM for its use (TSR-626(e))";
        :>> mechanism = "PLB";
        :>> timing = "per health report (≤ 0.1 s)";
        :>> verifMethod = "T-SIL, T-HIL";
    }
    requirement <'TSR-633'> tsr_633 : TechnicalSafetyRequirement {
        doc /* When driver awareness has reached zero (terminal DM alert) and the driver has not responded for 5 s, the item shall keep the lane and decelerate in lane to a standstill at 2 m/s², ramped in within j_down (TSR-202, TSR-205), about 15 s and 230 m from 110 km/h (register DQ-424, A, decided 2026-10-30), with the terminal alert sounding, then keep the vehicle stopped and held, and lock out re-engagement and resumption until the driver responds, so that the item cannot drive off again (register DQ-365, A, decided 2026-10-16). It shall not leave lateral and longitudinal control active at the set speed. */
        :>> workProduct = "WP-S-02";
        :>> allocText = "SoC";
        :>> asil = "A (SG-08; allocated to the QM SoC, open: WP-C-04 OI-11)";
        :>> mechanism = "FR, WRN";
        :>> timing = "reaction starts ≤ 5 s after the terminal alert (WP-S-04 §3.8)";
        :>> verifMethod = "T-SIL, T-VEH";
    }
    requirement <'TSR-634'> tsr_634 : TechnicalSafetyRequirement {
        doc /* When driver monitoring has fallen back to the wheel-touch policy (camera confidence too low), the escalation times of TSR-608 shall shorten as vehicle speed rises, so that the distance driven without driver supervision up to each alert stays within a bound set in WP-C-08 §5.4; at highway speed the time to the strongest alert shall be shorter than the fixed 25 s (register DQ-077, A, decided 2026-10-14). The speed table and the bound are set in WP-C-08 §5.4 (DMP-05) and validated under WP-V-02. */
        :>> workProduct = "WP-S-02";
        :>> allocText = "SoC";
        :>> asil = "A (SG-08; allocated to the QM SoC, open: WP-C-04 OI-11)";
        :>> mechanism = "WRN";
        :>> timing = "alert k at T_k = 5/15/25 s or D_k = 150/240/395 m since the last driver input, whichever comes first (WP-C-08 §5.4)";
        :>> verifMethod = "T-SIL, T-VEH";
    }
    requirement <'TSR-635'> tsr_635 : TechnicalSafetyRequirement {
        doc /* The time from the driver's change of state (eyes off the road, or hands off under the wheel-touch policy) to the first driver alert shall be ≤ 6 s end to end, including camera frame time, DM model latency and policy evaluation, so the first-alert timer of TSR-608 and TSR-634 shall leave a stated budget for that latency; the no-response reaction of TSR-611 shall start within the time set in WP-S-04 (assurance/03-system/WP-S-04-timing-ftti-budget.md). */
        :>> workProduct = "WP-S-02";
        :>> allocText = "SoC";
        :>> asil = "A (SG-08; allocated to the QM SoC, open: WP-C-04 OI-11)";
        :>> mechanism = "WRN";
        :>> timing = "first alert ≤ 6 s end to end";
        :>> verifMethod = "T-SIL, T-VEH";
    }
    requirement <'TSR-701'> tsr_701 : TechnicalSafetyRequirement {
        doc /* The harness orientation (normal, flipped, not connected) shall be detected before the relay is driven, and CAN routing and relay/ignition pin assignment shall follow it; loss or change of orientation while the relay is driven shall lead to SS-S. */
        :>> workProduct = "WP-S-02";
        :>> allocText = "P-HW, HAR, P-SW";
        :>> asil = "B";
        :>> mechanism = "PLB";
        :>> timing = "≤ 1 s";
        :>> verifMethod = "T-HIL, FI";
    }
    requirement <'TSR-702'> tsr_702 : TechnicalSafetyRequirement {
        doc /* With the relay de-energised, the harness shall connect the forward camera to the vehicle CAN without any active component in the path. */
        :>> workProduct = "WP-S-02";
        :>> allocText = "HAR";
        :>> asil = "B";
        :>> mechanism = "DES";
        :>> timing = "continuous";
        :>> verifMethod = "A, T-HIL";
    }
    requirement <'TSR-703'> tsr_703 : TechnicalSafetyRequirement {
        doc /* Harness connectors shall be keyed and latched so that partial insertion is detected (not-connected status) or cannot occur. */
        :>> workProduct = "WP-S-02";
        :>> allocText = "HAR";
        :>> asil = "B";
        :>> mechanism = "DES";
        :>> timing = "—";
        :>> verifMethod = "A, R";
    }
    requirement <'TSR-704'> tsr_704 : TechnicalSafetyRequirement {
        doc /* The envelope shall forward every camera-side frame to the car side unchanged, except STEERING_LKA 0x2E4, STEERING_LTA 0x191, LKAS_HUD 0x412 and (openpilot longitudinal) ACC_CONTROL 0x343, and shall forward every car-side frame to the camera side. */
        :>> workProduct = "WP-S-02";
        :>> allocText = "P-SW";
        :>> asil = "B";
        :>> mechanism = "DES";
        :>> timing = "continuous";
        :>> verifMethod = "T-SIL, T-HIL";
    }
    requirement <'TSR-705'> tsr_705 : TechnicalSafetyRequirement {
        doc /* In the reference configuration the envelope shall not accept from the SoC any frame on the car-side bus that the stock PCS function uses or that only a DSU would send: PRE_COLLISION 0x283, PRE_COLLISION_2 0x344, PCS_HUD 0x411, and the DSU messages 0x2E6, 0x2E7, 0x33E, 0x365, 0x366, 0x4CB and the bus-1 DSU set; if any is kept for a documented reason, its content shall be restricted to the inactive value. */
        :>> workProduct = "WP-S-02";
        :>> allocText = "P-SW";
        :>> asil = "B";
        :>> mechanism = "GATE";
        :>> timing = "per frame";
        :>> verifMethod = "R, T-SIL";
    }
    requirement <'TSR-706'> tsr_706 : TechnicalSafetyRequirement {
        doc /* On SS-S, any MCU fault, MCU reset, loss of device power or harness supply, the relay shall return to the stock camera-to-vehicle connection. */
        :>> workProduct = "WP-S-02";
        :>> allocText = "HAR, P-HW, P-SW";
        :>> asil = "B";
        :>> mechanism = "FR";
        :>> timing = "≤ 0.1 s after fault reaction";
        :>> verifMethod = "A, T-HIL, FI";
    }
    requirement <'TSR-707'> tsr_707 : TechnicalSafetyRequirement {
        doc /* Forwarded camera-side frames shall be delivered to the car side without loss and with a latency ≤ 1 ms (TBD from the PCS timing analysis) under worst-case bus and SPI load; forwarding queue overflow shall be detected and reported. */
        :>> workProduct = "WP-S-02";
        :>> allocText = "P-SW";
        :>> asil = "B";
        :>> mechanism = "TMO, PLB";
        :>> timing = "continuous";
        :>> verifMethod = "A, T-HIL";
    }
    requirement <'TSR-708'> tsr_708 : TechnicalSafetyRequirement {
        doc /* PCS/AEB braking shall have priority over 0x343 requests in the PCM, and PCS shall work with the harness installed. (External measure.) */
        :>> workProduct = "WP-S-02";
        :>> allocText = "EXT";
        :>> asil = "ext";
        :>> mechanism = "EXTM";
        :>> timing = "—";
        :>> verifMethod = "T-VEH";
    }
    requirement <'TSR-709'> tsr_709 : TechnicalSafetyRequirement {
        doc /* The SoC shall inform the driver when the stock system reports an AEB or FCW event. */
        :>> workProduct = "WP-S-02";
        :>> allocText = "SoC";
        :>> asil = "QM";
        :>> mechanism = "WRN";
        :>> timing = "≤ 0.2 s";
        :>> verifMethod = "T-SIL";
    }
    requirement <'TSR-710'> tsr_710 : TechnicalSafetyRequirement {
        doc /* The envelope shall detect a relay malfunction (any check_relay control message seen on the car side after the relay transition window) and inhibit all actuation TX and forwarding. */
        :>> workProduct = "WP-S-02";
        :>> allocText = "P-SW";
        :>> asil = "C";
        :>> mechanism = "PLB, FR";
        :>> timing = "detect: first offending frame after ≤ 1–2 s window / same frame";
        :>> verifMethod = "T-SIL, T-HIL";
    }
    requirement <'TSR-711'> tsr_711 : TechnicalSafetyRequirement {
        doc /* While the relay intercepts, the envelope shall supervise forwarding from the camera side to the car side and release the relay (TSR-706) when forwarding has stopped: no camera-side frame received or none forwarded for longer than t_fwd while the camera-side bus was active before, camera-side bus-off or error-passive, or forwarding queue overflow. t_fwd shall be set from the measured camera-side message periods so that detection stays within the SG-07 FDTI of ≤ 0.1 s. */
        :>> workProduct = "WP-S-02";
        :>> allocText = "P-SW";
        :>> asil = "B";
        :>> mechanism = "TMO, FR";
        :>> timing = "detect ≤ 0.1 s / release ≤ 0.1 s (SG-07, WP-S-04 §3.6)";
        :>> verifMethod = "T-HIL, FI";
    }
    requirement <'TSR-712'> tsr_712 : TechnicalSafetyRequirement {
        doc /* If the harness state readback (TSR-506) shows that the camera path stays intercepted when the release is commanded, the envelope shall inhibit all actuation TX, keep the fault latched until power cycle and report it; the SoC shall then give a warning that stock PCS/AEB is unavailable and prevent engagement until the harness is repaired. */
        :>> workProduct = "WP-S-02";
        :>> allocText = "P-SW, SoC";
        :>> asil = "B (envelope detection and inhibit); QM (B-sup: TSR-506) for the SoC warning";
        :>> mechanism = "PLB, FR, WRN";
        :>> timing = "detect ≤ 0.3 s (TSR-506) / warn ≤ 1 s";
        :>> verifMethod = "T-HIL, FI";
    }
    requirement <'TSR-713'> tsr_713 : TechnicalSafetyRequirement {
        doc /* While the stock system reports an AEB event (stockAeb), the SoC shall request zero acceleration in ACC_CONTROL 0x343 (no positive acceleration), keep that request for as long as the event is reported, and then return to normal control; the alert of TSR-709 is unchanged. Stock AEB braking keeps its priority in the PCM (TSR-708, AOU-04R), which is still tested. (Decided 2026-10-18, DQ-300 A; SFM-ACT-020.) */
        :>> workProduct = "WP-S-02";
        :>> allocText = "SoC";
        :>> asil = "QM (no ASIL claim; TSR-708 stays the measure)";
        :>> mechanism = "FR";
        :>> timing = "from the first frame that reports the event";
        :>> verifMethod = "T-SIL, T-VEH";
    }
    requirement <'TSR-801'> tsr_801 : TechnicalSafetyRequirement {
        doc /* Only a released LionDriver baseline shall be installed: the installed openpilot commit, AGNOS version and model artefact hashes shall equal the release record, and the build shall not be dirty. */
        :>> workProduct = "WP-S-06";
        :>> allocText = "OPS";
        :>> asil = "B‡";
        :>> mechanism = "";
        :>> timing = "";
        :>> verifMethod = "R-SW record, second-person check";
    }
    requirement <'TSR-802'> tsr_802 : TechnicalSafetyRequirement {
        doc /* The panda firmware shall be the release-signed, non-debug build recorded in the release record; its version string and signature shall be compared before first engagement. */
        :>> workProduct = "WP-S-06";
        :>> allocText = "OPS";
        :>> asil = "B‡";
        :>> mechanism = "";
        :>> timing = "";
        :>> verifMethod = "R-SW";
    }
    requirement <'TSR-803'> tsr_803 : TechnicalSafetyRequirement {
        doc /* Every vehicle ECU firmware version (engine, EPS, ABS, radar, camera) shall equal the reference record before engagement; a mismatch shall put the item in dashcam mode until an impact analysis extends the scope. */
        :>> workProduct = "WP-S-06";
        :>> allocText = "OPS";
        :>> asil = "B‡";
        :>> mechanism = "";
        :>> timing = "";
        :>> verifMethod = "R-CFG raw FW query output";
    }
    requirement <'TSR-804'> tsr_804 : TechnicalSafetyRequirement {
        doc /* The installed configuration shall show fingerprint TOYOTA_COROLLA_TSS2 (exact, not fuzzy), safety model toyota, safety parameter 73, alternative experience 0, openpilot longitudinal on, both in carParams and in pandaStates. */
        :>> workProduct = "WP-S-06";
        :>> allocText = "OPS";
        :>> asil = "B‡";
        :>> mechanism = "";
        :>> timing = "";
        :>> verifMethod = "R-CFG";
    }
    requirement <'TSR-805'> tsr_805 : TechnicalSafetyRequirement {
        doc /* Harness seating and the relay intercept/PCS-forwarding function shall be verified at installation: no relay malfunction or CAN errors, intercepted messages absent on the car side, PCS-relevant camera messages present on the car side with LD-SDA disengaged. */
        :>> workProduct = "WP-S-06";
        :>> allocText = "OPS";
        :>> asil = "B";
        :>> mechanism = "";
        :>> timing = "";
        :>> verifMethod = "R-INS, R-FUN";
    }
    requirement <'TSR-806'> tsr_806 : TechnicalSafetyRequirement {
        doc /* The parameter set shall equal the release record: Experimental Mode per D-08, DisengageOnAccelerator per WP-C-08, debug/maneuver/joystick modes absent, DM demo mode off, SSH off. */
        :>> workProduct = "WP-S-06";
        :>> allocText = "OPS";
        :>> asil = "QM (B-sup)";
        :>> mechanism = "";
        :>> timing = "";
        :>> verifMethod = "R-SW parameter dump";
    }
    requirement <'TSR-807'> tsr_807 : TechnicalSafetyRequirement {
        doc /* The device shall be mounted within the position tolerance and calibrated within the angle tolerance band derived from the model validation range. */
        :>> workProduct = "WP-S-06";
        :>> allocText = "OPS";
        :>> asil = "QM (SOTIF)";
        :>> mechanism = "";
        :>> timing = "";
        :>> verifMethod = "R-CAL";
    }
    requirement <'TSR-808'> tsr_808 : TechnicalSafetyRequirement {
        doc /* Vehicle service actions that can invalidate an AoU or the calibration (alignment/steering/suspension, EPS or ECM/ABS replacement or reflash, windscreen, camera or radar work, tyre size, brake repair, collision repair, battery disconnection, scan-tool sessions, aftermarket accessories) shall trigger the re-verification defined for that action before the item is engaged again. */
        :>> workProduct = "WP-S-06";
        :>> allocText = "OPS";
        :>> asil = "B‡";
        :>> mechanism = "";
        :>> timing = "";
        :>> verifMethod = "R-CAL / R-CFG / R-FUN as listed";
    }
    requirement <'TSR-809'> tsr_809 : TechnicalSafetyRequirement {
        doc /* The reference-configuration check (INS-21…INS-23), PCS-preservation check (INS-27) and harness inspection shall be repeated at least every 6 months and after any service trigger; harness and camera windows inspected monthly. */
        :>> workProduct = "WP-S-06";
        :>> allocText = "OPS";
        :>> asil = "B";
        :>> mechanism = "";
        :>> timing = "";
        :>> verifMethod = "Maintenance log";
    }
    requirement <'TSR-810'> tsr_810 : TechnicalSafetyRequirement {
        doc /* Only released baselines shall be installed by update; until signed updates exist, automatic updates shall be disabled and updates installed manually, followed by INS-15…INS-23; model-weight changes require SOTIF re-evaluation; envelope changes require the envelope verification evidence; parameters shall be re-checked after each update; a withdrawn release shall be replaced or the item put in dashcam mode. */
        :>> workProduct = "WP-S-06";
        :>> allocText = "OPS";
        :>> asil = "B‡";
        :>> mechanism = "";
        :>> timing = "";
        :>> verifMethod = "Release record (WP-K-06)";
    }
    requirement <'TSR-811'> tsr_811 : TechnicalSafetyRequirement {
        doc /* Before every drive the driver shall perform the pre-drive checks and shall not engage if a check fails (vehicle warning lamps, VSC on, clean camera area, device seated, DM camera unobstructed, no offroad alert, driver fit). */
        :>> workProduct = "WP-S-06";
        :>> allocText = "OPS";
        :>> asil = "QM (B-sup)";
        :>> mechanism = "";
        :>> timing = "";
        :>> verifMethod = "Briefing acknowledgement";
    }
    requirement <'TSR-812'> tsr_812 : TechnicalSafetyRequirement {
        doc /* Each driver shall receive the user information and safety warnings before first use and acknowledge them; in the development phase only approved safety drivers shall operate the item. */
        :>> workProduct = "WP-S-06";
        :>> allocText = "OPS";
        :>> asil = "QM (B-sup)";
        :>> mechanism = "";
        :>> timing = "";
        :>> verifMethod = "R-USR";
    }
    requirement <'TSR-813'> tsr_813 : TechnicalSafetyRequirement {
        doc /* Field monitoring shall collect and analyse drive logs and driver reports of every installed item, including every disengagement caused by a safety mechanism (controlsMismatch, relayMalfunction, RX invalid, heartbeat lost, safetyTxBlocked > 0), and feed problem resolution and the safety case. */
        :>> workProduct = "WP-S-06";
        :>> allocText = "OPS";
        :>> asil = "QM";
        :>> mechanism = "";
        :>> timing = "";
        :>> verifMethod = "Monitoring reports";
    }
    requirement <'TSR-814'> tsr_814 : TechnicalSafetyRequirement {
        doc /* On removal of the item the stock camera connection shall be restored and stock TSS functions (LTA/LDA, DRCC, PCS) and the absence of DTCs verified; logs needed for field monitoring retrieved; device data, credentials and identity keys wiped or the device kept under LionDriver control with its history recorded. */
        :>> workProduct = "WP-S-06";
        :>> allocText = "OPS";
        :>> asil = "B (stock path); CS (data)";
        :>> mechanism = "";
        :>> timing = "";
        :>> verifMethod = "Decommissioning record";
    }
    requirement <'TSR-815'> tsr_815 : TechnicalSafetyRequirement {
        doc /* Only devices and harnesses of the approved hardware revision, with clean history, shall be installed; units returned after a field event or decommissioned from another vehicle shall pass refurbishment inspection first. */
        :>> workProduct = "WP-S-06";
        :>> allocText = "OPS";
        :>> asil = "B‡";
        :>> mechanism = "";
        :>> timing = "";
        :>> verifMethod = "R-DEV";
    }
    requirement <'TSR-816'> tsr_816 : TechnicalSafetyRequirement {
        doc /* Installation shall be done by a trained installer, and the installation record (R-DEV…R-USR) shall be complete and second-person checked before the first engagement and retained per WP-P-04. */
        :>> workProduct = "WP-S-06";
        :>> allocText = "OPS";
        :>> asil = "B‡";
        :>> mechanism = "";
        :>> timing = "";
        :>> verifMethod = "Record review";
    }
    requirement <'TSR-817'> tsr_817 : TechnicalSafetyRequirement {
        doc /* Item faults shall be handled by replacement, not repair: defective devices or harnesses shall be quarantined, reported and returned; after replacement the full provisioning and configuration steps shall be repeated. */
        :>> workProduct = "WP-S-06";
        :>> allocText = "OPS";
        :>> asil = "B‡";
        :>> mechanism = "";
        :>> timing = "";
        :>> verifMethod = "Problem report (WP-P-03)";
    }
    requirement <'TSR-818'> tsr_818 : TechnicalSafetyRequirement {
        doc /* At end of support of a release, every user shall be informed with the date after which the release must not be engaged. */
        :>> workProduct = "WP-S-06";
        :>> allocText = "OPS";
        :>> asil = "QM";
        :>> mechanism = "";
        :>> timing = "";
        :>> verifMethod = "Notification record";
    }
    requirement <'SYS-001'> sys_001 : SystemRequirement {
        doc /* While lateral control is active on a straight or curved road inside the ODD, the system shall keep the vehicle near the lane centre. */
        :>> workProduct = "WP-S-01";
        :>> allocText = "host.modeld, host.controlsd";
        :>> functionId = "F-01";
        :>> reqType = "P";
        :>> target = "Lateral offset from lane centre: p95 ≤ TBD (proposed 0.3 m), p99.9 ≤ TBD (proposed 0.6 m) per stratum";
        :>> verifMethod = "LOG, T-VEH";
    }
    requirement <'SYS-002'> sys_002 : SystemRequirement {
        doc /* The commanded lateral acceleration shall not exceed 3.0 m/s² (roll-compensated) and the lateral jerk shall not exceed 5 m/s³. */
        :>> workProduct = "WP-S-01";
        :>> allocText = "host.controlsd";
        :>> functionId = "F-01";
        :>> reqType = "C";
        :>> target = "as stated";
        :>> verifMethod = "T-SIL";
    }
    requirement <'SYS-003'> sys_003 : SystemRequirement {
        doc /* The system shall follow curves down to the radius R_ODD = v²/2.5 m/s² at the travel speed without saturating the steering command. */
        :>> workProduct = "WP-S-01";
        :>> allocText = "host.controlsd, host.selfdrived";
        :>> functionId = "F-01";
        :>> reqType = "P";
        :>> target = "No steerSaturated in curves ≥ R_ODD in ≥ TBD % of passes";
        :>> verifMethod = "T-VEH, LOG";
    }
    requirement <'SYS-004'> sys_004 : SystemRequirement {
        doc /* When the steering command saturates, the system shall warn the driver ("Turn Exceeds Steering Limit"). */
        :>> workProduct = "WP-S-01";
        :>> allocText = "host.selfdrived, host.hmi";
        :>> functionId = "F-01";
        :>> reqType = "H";
        :>> target = "Warning within ≤ 1 s of saturation";
        :>> verifMethod = "T-SIL";
    }
    requirement <'SYS-005'> sys_005 : SystemRequirement {
        doc /* An assisted lane change shall start only after the driver activates the turn signal and applies steering torque in the same direction, above 20 mph. */
        :>> workProduct = "WP-S-01";
        :>> allocText = "host.modeld";
        :>> functionId = "F-01";
        :>> reqType = "F";
        :>> target = "as stated";
        :>> verifMethod = "T-SIL";
    }
    requirement <'SYS-006'> sys_006 : SystemRequirement {
        doc /* An assisted lane change shall complete or be cancelled within 10 s of the turn signal; it shall be cancelled when the turn signal is released. */
        :>> workProduct = "WP-S-01";
        :>> allocText = "host.modeld";
        :>> functionId = "F-01";
        :>> reqType = "F";
        :>> target = "10 s";
        :>> verifMethod = "T-SIL";
    }
    requirement <'SYS-007'> sys_007 : SystemRequirement {
        doc /* Lateral control shall not be active at standstill and shall resume without a steering jump when the vehicle moves off. */
        :>> workProduct = "WP-S-01";
        :>> allocText = "host.controlsd";
        :>> functionId = "F-01";
        :>> reqType = "F";
        :>> target = "Torque change at resume within TSR-103 rate";
        :>> verifMethod = "T-SIL";
    }
    requirement <'SYS-008'> sys_008 : SystemRequirement {
        doc /* Lateral control shall not cause oscillation (weaving) on a straight road. */
        :>> workProduct = "WP-S-01";
        :>> allocText = "host.controlsd, estimators";
        :>> functionId = "F-01";
        :>> reqType = "P";
        :>> target = "Lateral offset spectral peak 0.2–2 Hz below TBD";
        :>> verifMethod = "LOG, T-VEH";
    }
    requirement <'SYS-020'> sys_020 : SystemRequirement {
        doc /* The system shall hold the set speed within ±TBD km/h on level road without a lead. */
        :>> workProduct = "WP-S-01";
        :>> allocText = "host.plannerd";
        :>> functionId = "F-02";
        :>> reqType = "P";
        :>> target = "proposed ±2 km/h";
        :>> verifMethod = "T-VEH";
    }
    requirement <'SYS-021'> sys_021 : SystemRequirement {
        doc /* The set-speed range shall be the PCM cruise set range of the reference vehicle, and shall not exceed the ODD speed bound of 110 km/h (ODD-H, DQ-260; the arterial ODD-A was dropped, DQ-023). */
        :>> workProduct = "WP-S-01";
        :>> allocText = "host.card";
        :>> functionId = "F-02";
        :>> reqType = "C";
        :>> target = "as stated";
        :>> verifMethod = "R, T-VEH";
    }
    requirement <'SYS-022'> sys_022 : SystemRequirement {
        doc /* When following a lead, the system shall keep a time gap equal to the selected personality: relaxed 1.75 s, standard 1.45 s, aggressive 1.25 s. */
        :>> workProduct = "WP-S-01";
        :>> allocText = "host.plannerd";
        :>> functionId = "F-02";
        :>> reqType = "P";
        :>> target = "steady-state gap error ≤ TBD";
        :>> verifMethod = "T-VEH, LOG";
    }
    requirement <'SYS-023'> sys_023 : SystemRequirement {
        doc /* The default personality in the reference configuration shall be "standard" or "relaxed", not "aggressive". */
        :>> workProduct = "WP-S-01";
        :>> allocText = "host.manager";
        :>> functionId = "F-02";
        :>> reqType = "C";
        :>> target = "as stated";
        :>> verifMethod = "R";
    }
    requirement <'SYS-024'> sys_024 : SystemRequirement {
        doc /* The system shall bring the vehicle to a stop behind a stopping lead, keeping a stopped distance of about 6 m, and hold it at standstill. */
        :>> workProduct = "WP-S-01";
        :>> allocText = "host.plannerd, host.card";
        :>> functionId = "F-02";
        :>> reqType = "F/P";
        :>> target = "stop distance 6 m ± TBD";
        :>> verifMethod = "T-VEH";
    }
    requirement <'SYS-025'> sys_025 : SystemRequirement {
        doc /* After a standstill, the system shall resume automatically when the lead moves off, within TBD s; without a lead, it shall not move off without a driver action. */
        :>> workProduct = "WP-S-01";
        :>> allocText = "host.card";
        :>> functionId = "F-02";
        :>> reqType = "F";
        :>> target = "as stated";
        :>> verifMethod = "T-VEH";
    }
    requirement <'SYS-026'> sys_026 : SystemRequirement {
        doc /* Comfort: in normal following, the commanded acceleration shall stay within the cruise limits (1.6→0.6 m/s² by speed, −1.2 m/s² cruise braking) and use stronger braking only for lead-following, down to −3.5 m/s². */
        :>> workProduct = "WP-S-01";
        :>> allocText = "host.plannerd";
        :>> functionId = "F-02";
        :>> reqType = "P";
        :>> target = "as stated";
        :>> verifMethod = "T-SIL";
    }
    requirement <'SYS-027'> sys_027 : SystemRequirement {
        doc /* Experimental Mode (end-to-end longitudinal) shall be disabled and not selectable in the reference configuration until decision D-08 includes it. */
        :>> workProduct = "WP-S-01";
        :>> allocText = "host.manager, host.hmi";
        :>> functionId = "F-02";
        :>> reqType = "C";
        :>> target = "Param default \"0\", toggle disabled";
        :>> verifMethod = "R, T-SIL";
    }
    requirement <'SYS-040'> sys_040 : SystemRequirement {
        doc /* Engagement shall be possible only through the stock cruise controls and only when no no-entry condition is present. In the reference configuration a setting outside the assured values (assured_config.py: following distance other than relaxed, CA-011; Experimental Mode on; alpha longitudinal; a debug or maneuver mode) is a no-entry condition, with a no-entry alert that names the setting (decided 2026-10-18, DQ-221 A; SWF-067, SWF-ACT-063). */
        :>> workProduct = "WP-S-01";
        :>> allocText = "host.selfdrived";
        :>> functionId = "F-03";
        :>> reqType = "F";
        :>> target = "as stated";
        :>> verifMethod = "T-SIL, T-VEH";
    }
    requirement <'SYS-041'> sys_041 : SystemRequirement {
        doc /* The system shall refuse engagement, with a no-entry alert, below the highway speed floor v_floor, and shall engage from v_floor up to the ODD speed bound. This is the entry check for the highways-only ODD (DQ-023) until road-type data exists (WP-C-07 FM-08). Once engaged, slowing below v_floor (traffic, stop-and-go) does not disengage. (Decided 2026-10-18, DQ-280 A; STPA LS-13.) */
        :>> workProduct = "WP-S-01";
        :>> allocText = "host.card";
        :>> functionId = "F-03";
        :>> reqType = "F";
        :>> target = "v_floor = TBD (proposed 60 km/h)";
        :>> verifMethod = "T-SIL, T-VEH";
    }
    requirement <'SYS-042'> sys_042 : SystemRequirement {
        doc /* A brake press or cancel shall disengage; the accelerator shall override longitudinal control without disengaging (reference setting). */
        :>> workProduct = "WP-S-01";
        :>> allocText = "host.selfdrived";
        :>> functionId = "F-03";
        :>> reqType = "F";
        :>> target = "as stated";
        :>> verifMethod = "T-VEH";
    }
    requirement <'SYS-043'> sys_043 : SystemRequirement {
        doc /* After start-up, the system shall be ready to engage within TBD s of ignition on. */
        :>> workProduct = "WP-S-01";
        :>> allocText = "host.selfdrived, hardwared";
        :>> functionId = "F-03";
        :>> reqType = "P";
        :>> target = "proposed ≤ 30 s";
        :>> verifMethod = "T-VEH";
    }
    requirement <'SYS-060'> sys_060 : SystemRequirement {
        doc /* Above 10 km/h, DM shall warn a visually distracted driver with escalating alerts at 5, 8 and 13 s (vision policy) or 5, 15 and 25 s (wheel-touch policy). */
        :>> workProduct = "WP-S-01";
        :>> allocText = "host.dm";
        :>> functionId = "F-04";
        :>> reqType = "H";
        :>> target = "as stated";
        :>> verifMethod = "T-SIL, T-VEH";
    }
    requirement <'SYS-061'> sys_061 : SystemRequirement {
        doc /* DM classification performance shall meet AIR-07/AIR-08 of WP-C-11. */
        :>> workProduct = "WP-S-01";
        :>> allocText = "host.dm";
        :>> functionId = "F-04";
        :>> reqType = "P";
        :>> target = "recall ≥ 95 % gaze-off > 2 s; false distraction ≤ 1/h (confirmed, WP-C-08 OI-2)";
        :>> verifMethod = "LOG";
    }
    requirement <'SYS-062'> sys_062 : SystemRequirement {
        doc /* DM shall work in the ODD lighting conditions (day, dusk, night with IR) and with sunglasses, or fall back to the wheel-touch policy. */
        :>> workProduct = "WP-S-01";
        :>> allocText = "host.dm";
        :>> functionId = "F-04";
        :>> reqType = "P";
        :>> target = "fallback triggered when uncertain; coverage TBD";
        :>> verifMethod = "T-VEH, LOG";
    }
    requirement <'SYS-063'> sys_063 : SystemRequirement {
        doc /* On no response to the highest alert, the system shall slow the vehicle, disengage and lock out re-engagement (1/5/15/30 min). */
        :>> workProduct = "WP-S-01";
        :>> allocText = "host.dm, host.controlsd";
        :>> functionId = "F-04";
        :>> reqType = "F";
        :>> target = "as stated";
        :>> verifMethod = "T-SIL, T-VEH";
    }
    requirement <'SYS-080'> sys_080 : SystemRequirement {
        doc /* The engaged/disengaged state shall be shown continuously on the device and through the cluster cruise indicator and LKAS HUD. */
        :>> workProduct = "WP-S-01";
        :>> allocText = "host.hmi, host.card";
        :>> functionId = "F-05";
        :>> reqType = "H";
        :>> target = "as stated";
        :>> verifMethod = "T-VEH";
    }
    requirement <'SYS-081'> sys_081 : SystemRequirement {
        doc /* An alert shall be displayed and its sound started within ≤ 0.2 s of the event being raised by selfdrived. */
        :>> workProduct = "WP-S-01";
        :>> allocText = "host.selfdrived, host.hmi";
        :>> functionId = "F-05";
        :>> reqType = "P";
        :>> target = "p99 ≤ 0.2 s";
        :>> verifMethod = "T-HIL";
    }
    requirement <'SYS-082'> sys_082 : SystemRequirement {
        doc /* Alert text shall describe the actual cause. */
        :>> workProduct = "WP-S-01";
        :>> allocText = "host.selfdrived";
        :>> functionId = "F-05";
        :>> reqType = "H";
        :>> target = "Review of every alert used in the reference configuration";
        :>> verifMethod = "R";
    }
    requirement <'SYS-083'> sys_083 : SystemRequirement {
        doc /* Alerts and sounds shall be perceivable at highway noise levels. */
        :>> workProduct = "WP-S-01";
        :>> allocText = "host.hmi";
        :>> functionId = "F-05";
        :>> reqType = "P";
        :>> target = "sound level ≥ TBD dB(A) above cabin noise";
        :>> verifMethod = "T-VEH";
    }
    requirement <'SYS-100'> sys_100 : SystemRequirement {
        doc /* FCW shall alert when the model predicts hard braking or the planner predicts a collision. */
        :>> workProduct = "WP-S-01";
        :>> allocText = "host.selfdrived, host.modeld";
        :>> functionId = "F-06, F-07";
        :>> reqType = "F";
        :>> target = "as stated";
        :>> verifMethod = "T-SIL";
    }
    requirement <'SYS-101'> sys_101 : SystemRequirement {
        doc /* FCW false alert rate shall be ≤ TBD per 1000 km. */
        :>> workProduct = "WP-S-01";
        :>> allocText = "host.selfdrived";
        :>> functionId = "F-06, F-07";
        :>> reqType = "P";
        :>> target = "TBD";
        :>> verifMethod = "LOG";
    }
    requirement <'SYS-102'> sys_102 : SystemRequirement {
        doc /* LDW shall warn when not laterally engaged, above 31 mph, with no turn signal in the last 5 s, when the vehicle drifts toward a visible lane line. */
        :>> workProduct = "WP-S-01";
        :>> allocText = "host.plannerd";
        :>> functionId = "F-06, F-07";
        :>> reqType = "F";
        :>> target = "as stated";
        :>> verifMethod = "T-SIL";
    }
    requirement <'SYS-120'> sys_120 : SystemRequirement {
        doc /* In normal operation inside the ODD, the envelope shall not reject any command produced by the SoC controller (no false interventions). */
        :>> workProduct = "WP-S-01";
        :>> allocText = "E-03a";
        :>> functionId = "F-08";
        :>> reqType = "P";
        :>> target = "safetyTxBlocked increments per hour of engaged driving = 0 (excluding intentional tests, and excluding frames refused by design: STEERING_LKA frames refused by the EPS-fault gate at fault onset (TSR-110) and frames rejected by the TX rate supervision (TSR-518), reference build, added 2026-10-12)";
        :>> verifMethod = "LOG";
    }
    requirement <'SYS-121'> sys_121 : SystemRequirement {
        doc /* The envelope shall report its mode, parameter, authority state, fault flags and counters to the SoC at ≥ 10 Hz. */
        :>> workProduct = "WP-S-01";
        :>> allocText = "E-03b, host.pandad";
        :>> functionId = "F-08";
        :>> reqType = "I";
        :>> target = "as stated";
        :>> verifMethod = "T-HIL";
    }
    requirement <'SYS-140'> sys_140 : SystemRequirement {
        doc /* Every drive shall be logged in 60 s segments including CAN, carControl, selfdriveState, pandaStates and model outputs. */
        :>> workProduct = "WP-S-01";
        :>> allocText = "remoteAndLogging";
        :>> functionId = "F-09";
        :>> reqType = "F";
        :>> target = "as stated";
        :>> verifMethod = "T-SIL";
    }
    requirement <'SYS-141'> sys_141 : SystemRequirement {
        doc /* Logs shall identify the software release, panda firmware version and model artefacts in use. */
        :>> workProduct = "WP-S-01";
        :>> allocText = "remoteAndLogging";
        :>> functionId = "F-09";
        :>> reqType = "F";
        :>> target = "as stated";
        :>> verifMethod = "R";
    }
    requirement <'SYS-142'> sys_142 : SystemRequirement {
        doc /* Segments flagged by the driver shall be preserved from automatic deletion. */
        :>> workProduct = "WP-S-01";
        :>> allocText = "remoteAndLogging";
        :>> functionId = "F-09";
        :>> reqType = "F";
        :>> target = "as stated";
        :>> verifMethod = "T-SIL";
    }
    requirement <'SYS-143'> sys_143 : SystemRequirement {
        doc /* Automatic deletion shall keep at least 5 GiB or 10 % of storage free. */
        :>> workProduct = "WP-S-01";
        :>> allocText = "remoteAndLogging";
        :>> functionId = "F-09";
        :>> reqType = "C";
        :>> target = "as stated";
        :>> verifMethod = "T-SIL";
    }
    requirement <'SYS-144'> sys_144 : SystemRequirement {
        doc /* Uploads, remote access and software updates shall be configurable to the LionDriver policy and shall not run while onroad unless the policy allows it. */
        :>> workProduct = "WP-S-01";
        :>> allocText = "remoteAndLogging, host.manager";
        :>> functionId = "F-09";
        :>> reqType = "C";
        :>> target = "as stated";
        :>> verifMethod = "R, T-SIL";
    }
    requirement <'SYS-145'> sys_145 : SystemRequirement {
        doc /* With automatic updates disabled, the system shall not block engagement because of missing update connectivity. */
        :>> workProduct = "WP-S-01";
        :>> allocText = "remoteAndLogging, hardwared";
        :>> functionId = "F-09";
        :>> reqType = "F";
        :>> target = "as stated";
        :>> verifMethod = "T-VEH";
    }
    requirement <'CSR-011'> csr_011 : CybersecurityRequirement {
        doc /* Release panda firmware for the reference configuration shall accept a car safety mode only if model, parameter and alternative experience equal the compile-time locked values recorded in the release record. */
        :>> workProduct = "WP-S-07";
        :>> allocText = "FW";
        :>> group = "CSR-C-01";
        :>> groupTitle = "Safety configuration lock (CSG-01, CAL 3)";
        :>> safetyRelation = "TSR-512, FSR-01.10, B‡";
        :>> verifMethod = "R, UT, HIL";
        :>> status = "in";
    }
    requirement <'CSR-012'> csr_012 : CybersecurityRequirement {
        doc /* A rejected safety-configuration request shall leave the panda in a non-actuating mode and set a fault flag reported to the SoC in the health packet. */
        :>> workProduct = "WP-S-07";
        :>> allocText = "FW";
        :>> group = "CSR-C-01";
        :>> groupTitle = "Safety configuration lock (CSG-01, CAL 3)";
        :>> safetyRelation = "TSR-512, B‡";
        :>> verifMethod = "UT, HIL";
        :>> status = "partly";
    }
    requirement <'CSR-013'> csr_013 : CybersecurityRequirement {
        doc /* Transitions from the locked car mode to SILENT or NOOUTPUT shall remain permitted at all times. */
        :>> workProduct = "WP-S-07";
        :>> allocText = "FW";
        :>> group = "CSR-C-01";
        :>> groupTitle = "Safety configuration lock (CSG-01, CAL 3)";
        :>> safetyRelation = "TSR-512, B‡ (safe state reachable)";
        :>> verifMethod = "UT, HIL";
        :>> status = "in";
    }
    requirement <'CSR-014'> csr_014 : CybersecurityRequirement {
        doc /* While a car safety mode is active, release firmware shall reject host commands outside a documented allow-list, including relay drive (0xc5), CAN mode/speed changes (0xdb, 0xde) and loopback. */
        :>> workProduct = "WP-S-07";
        :>> allocText = "FW";
        :>> group = "CSR-C-01";
        :>> groupTitle = "Safety configuration lock (CSG-01, CAL 3)";
        :>> safetyRelation = "TSR-513, B‡";
        :>> verifMethod = "R, UT, FZ";
        :>> status = "partly";
    }
    requirement <'CSR-015'> csr_015 : CybersecurityRequirement {
        doc /* Alternative experience shall not be changeable in release firmware for the reference configuration. */
        :>> workProduct = "WP-S-07";
        :>> allocText = "FW";
        :>> group = "CSR-C-01";
        :>> groupTitle = "Safety configuration lock (CSG-01, CAL 3)";
        :>> safetyRelation = "TSR-512, TSR-804";
        :>> verifMethod = "UT";
        :>> status = "in";
    }
    requirement <'CSR-016'> csr_016 : CybersecurityRequirement {
        doc /* pandad shall compare the panda-reported safety model, parameter and alternative experience with the release-record values and prevent engagement and raise an alert on mismatch. */
        :>> workProduct = "WP-S-07";
        :>> allocText = "SoC";
        :>> group = "CSR-C-01";
        :>> groupTitle = "Safety configuration lock (CSG-01, CAL 3)";
        :>> safetyRelation = "QM (B-sup: TSR-512); no matching TSR-6xx (proposed addition, OI-1). 2026-10-12: TSR-619 of WP-S-02 now refines this CSR";
        :>> verifMethod = "UT, HIL";
        :>> status = "not";
    }
    requirement <'CSR-021'> csr_021 : CybersecurityRequirement {
        doc /* The release panda firmware and bootstub shall be built with RELEASE and the LionDriver certificate, and the release build shall fail if ALLOW_DEBUG is defined. */
        :>> workProduct = "WP-S-07";
        :>> allocText = "FW; ENV";
        :>> group = "CSR-C-02";
        :>> groupTitle = "No debug capability in release firmware (CSG-01/CSG-02, CAL 3)";
        :>> safetyRelation = "TSR-514, FSR-01.10, B‡";
        :>> verifMethod = "BA";
        :>> status = "not";
    }
    requirement <'CSR-022'> csr_022 : CybersecurityRequirement {
        doc /* The release bootstub shall not contain the debug public key and shall accept no key other than the LionDriver release key. */
        :>> workProduct = "WP-S-07";
        :>> allocText = "FW";
        :>> group = "CSR-C-02";
        :>> groupTitle = "No debug capability in release firmware (CSG-01/CSG-02, CAL 3)";
        :>> safetyRelation = "TSR-514, B‡";
        :>> verifMethod = "BA, HIL";
        :>> status = "partly";
    }
    requirement <'CSR-023'> csr_023 : CybersecurityRequirement {
        doc /* Debug-only host commands (relay drive 0xc5, ALLOUTPUT mode, bootloader entry, debug sleep) shall be absent from release firmware. */
        :>> workProduct = "WP-S-07";
        :>> allocText = "FW";
        :>> group = "CSR-C-02";
        :>> groupTitle = "No debug capability in release firmware (CSG-01/CSG-02, CAL 3)";
        :>> safetyRelation = "TSR-514, TSR-513, HWSR-506c";
        :>> verifMethod = "BA, R, FZ";
        :>> status = "partly";
    }
    requirement <'CSR-024'> csr_024 : CybersecurityRequirement {
        doc /* Softloader entry (0xd1 param 1) shall be accepted only while the panda is in a non-actuating mode and no car mode has been active in the current ignition cycle (refused after a drive this ignition cycle). */
        :>> workProduct = "WP-S-07";
        :>> allocText = "FW";
        :>> group = "CSR-C-02";
        :>> groupTitle = "No debug capability in release firmware (CSG-01/CSG-02, CAL 3)";
        :>> safetyRelation = "TSR-511 (softloader refused in car mode), B‡; ignition-off condition is an additional CS constraint";
        :>> verifMethod = "UT, HIL";
        :>> status = "partly";
    }
    requirement <'CSR-031'> csr_031 : CybersecurityRequirement {
        doc /* The bootstub shall verify the application image with an ECDSA signature over P-256 and a SHA-256 digest (128-bit security strength; decided 2026-10-19, DQ-191 A) before transferring control. */
        :>> workProduct = "WP-S-07";
        :>> allocText = "FW";
        :>> group = "CSR-C-03";
        :>> groupTitle = "Authenticated firmware boot (CSG-02, CAL 3)";
        :>> safetyRelation = "TSR-511, C";
        :>> verifMethod = "R, HIL";
        :>> status = "not";
    }
    requirement <'CSR-032'> csr_032 : CybersecurityRequirement {
        doc /* The verifying public key shall be the LionDriver panda release key, whose private key is generated and held offline and never stored in the repository, CI or logs. */
        :>> workProduct = "WP-S-07";
        :>> allocText = "FW; ENV";
        :>> group = "CSR-C-03";
        :>> groupTitle = "Authenticated firmware boot (CSG-02, CAL 3)";
        :>> safetyRelation = "TSR-511, TSR-514";
        :>> verifMethod = "CM, PR";
        :>> status = "not";
    }
    requirement <'CSR-033'> csr_033 : CybersecurityRequirement {
        doc /* The bootstub shall reject an image whose version is below a minimum version held in write-protected storage. */
        :>> workProduct = "WP-S-07";
        :>> allocText = "FW";
        :>> group = "CSR-C-03";
        :>> groupTitle = "Authenticated firmware boot (CSG-02, CAL 3)";
        :>> safetyRelation = "TSR-511";
        :>> verifMethod = "UT, HIL";
        :>> status = "partly";
    }
    requirement <'CSR-034'> csr_034 : CybersecurityRequirement {
        doc /* The application image integrity shall be re-checked at start-up and periodically at run time, with mismatch leading to the safe state. */
        :>> workProduct = "WP-S-07";
        :>> allocText = "FW";
        :>> group = "CSR-C-03";
        :>> groupTitle = "Authenticated firmware boot (CSG-02, CAL 3)";
        :>> safetyRelation = "TSR-503, TSR-515, HWSR-503c, B‡";
        :>> verifMethod = "HIL, FI";
        :>> status = "not";
    }
    requirement <'CSR-041'> csr_041 : CybersecurityRequirement {
        doc /* The panda option bytes shall be set at provisioning to an RDP level chosen by CS-AD-02 that prevents read-out and debug-port access to the firmware. */
        :>> workProduct = "WP-S-07";
        :>> allocText = "FW; USR";
        :>> group = "CSR-C-04";
        :>> groupTitle = "Flash protection (CSG-02, CAL 3)";
        :>> safetyRelation = "TSR-511, HWSR-502c";
        :>> verifMethod = "HIL (option-byte read), PR";
        :>> status = "not";
    }
    requirement <'CSR-042'> csr_042 : CybersecurityRequirement {
        doc /* Write protection shall be set on the bootstub sector(s) so that neither the application nor the softloader can modify them. */
        :>> workProduct = "WP-S-07";
        :>> allocText = "FW; USR";
        :>> group = "CSR-C-04";
        :>> groupTitle = "Flash protection (CSG-02, CAL 3)";
        :>> safetyRelation = "TSR-511";
        :>> verifMethod = "HIL";
        :>> status = "not";
    }
    requirement <'CSR-043'> csr_043 : CybersecurityRequirement {
        doc /* Installation shall record the option-byte values and the bootstub and application hashes, and compare them with the release record. */
        :>> workProduct = "WP-S-07";
        :>> allocText = "USR";
        :>> group = "CSR-C-04";
        :>> groupTitle = "Flash protection (CSG-02, CAL 3)";
        :>> safetyRelation = "TSR-802";
        :>> verifMethod = "PR";
        :>> status = "not";
    }
    requirement <'CSR-051'> csr_051 : CybersecurityRequirement {
        doc /* Release pandad shall not flash a development bootstub; recovery shall flash only the release-signed bootstub and application of the installed release. */
        :>> workProduct = "WP-S-07";
        :>> allocText = "SoC";
        :>> group = "CSR-C-05";
        :>> groupTitle = "No unauthenticated recovery path (CSG-02, CAL 3)";
        :>> safetyRelation = "TSR-511";
        :>> verifMethod = "R, HIL";
        :>> status = "not";
    }
    requirement <'CSR-052'> csr_052 : CybersecurityRequirement {
        doc /* SoC use of STM_BOOT0 for recovery shall occur only on explicit offroad owner action and shall be logged as a security event. */
        :>> workProduct = "WP-S-07";
        :>> allocText = "SoC; USR";
        :>> group = "CSR-C-05";
        :>> groupTitle = "No unauthenticated recovery path (CSG-02, CAL 3)";
        :>> safetyRelation = "TSR-511";
        :>> verifMethod = "R, HIL";
        :>> status = "not";
    }
    requirement <'CSR-053'> csr_053 : CybersecurityRequirement {
        doc /* pandad shall not set a car safety mode unless the panda reports the firmware version and signature recorded in the release record. */
        :>> workProduct = "WP-S-07";
        :>> allocText = "SoC";
        :>> group = "CSR-C-05";
        :>> groupTitle = "No unauthenticated recovery path (CSG-02, CAL 3)";
        :>> safetyRelation = "QM (B-sup: TSR-511); TSR-802 at installation";
        :>> verifMethod = "UT, HIL";
        :>> status = "partly";
    }
    requirement <'CSR-054'> csr_054 : CybersecurityRequirement {
        doc /* The architecture shall prevent SoC control of STM_BOOT0/STM_RST_N from resulting in execution of firmware not signed with the LionDriver release key, or the residual shall be recorded as a cybersecurity claim per CS-AD-03. */
        :>> workProduct = "WP-S-07";
        :>> allocText = "FW; SoC; USR";
        :>> group = "CSR-C-05";
        :>> groupTitle = "No unauthenticated recovery path (CSG-02, CAL 3)";
        :>> safetyRelation = "HWSR-502c, TSR-511";
        :>> verifMethod = "A, HIL";
        :>> status = "not";
    }
    requirement <'CSR-061'> csr_061 : CybersecurityRequirement {
        doc /* The panda envelope limits and checks shall not depend on any value from the SoC params store or msgq other than the locked safety configuration of CSR-011. */
        :>> workProduct = "WP-S-07";
        :>> allocText = "FW";
        :>> group = "CSR-C-06";
        :>> groupTitle = "Params and IPC (CSG-03, CAL 2)";
        :>> safetyRelation = "TSR-1xx/2xx/3xx, TSR-512, TSR-507; FFI (WP-A-02)";
        :>> verifMethod = "R, A";
        :>> status = "partly";
    }
    requirement <'CSR-062'> csr_062 : CybersecurityRequirement {
        doc /* Safety-relevant params (§3.8) shall be writable only by their designated writer processes, enforced by OS file permissions, and their values shall be checked against the release record at manager start with engagement blocked on mismatch. */
        :>> workProduct = "WP-S-07";
        :>> allocText = "SoC";
        :>> group = "CSR-C-06";
        :>> groupTitle = "Params and IPC (CSG-03, CAL 2)";
        :>> safetyRelation = "TSR-806 (installation check), QM";
        :>> verifMethod = "R, UT";
        :>> status = "not";
    }
    requirement <'CSR-063'> csr_063 : CybersecurityRequirement {
        doc /* Each safety-relevant msgq topic consumed by controlsd, selfdrived, plannerd or dmonitoringd shall be publishable only by its designated process, and a second publisher shall be detected and reported. */
        :>> workProduct = "WP-S-07";
        :>> allocText = "SoC";
        :>> group = "CSR-C-06";
        :>> groupTitle = "Params and IPC (CSG-03, CAL 2)";
        :>> safetyRelation = "QM; no TSR";
        :>> verifMethod = "R, UT";
        :>> status = "not";
    }
    requirement <'CSR-064'> csr_064 : CybersecurityRequirement {
        doc /* Network-facing processes (athenad, uploader, updated, webrtcd, UI) shall run without permission to write safety-relevant params or publish safety-relevant topics. */
        :>> workProduct = "WP-S-07";
        :>> allocText = "SoC";
        :>> group = "CSR-C-06";
        :>> groupTitle = "Params and IPC (CSG-03, CAL 2)";
        :>> safetyRelation = "— (likelihood reduction)";
        :>> verifMethod = "R, PT";
        :>> status = "check";
    }
    requirement <'CSR-071'> csr_071 : CybersecurityRequirement {
        doc /* Release builds shall not start the joystick, longitudinal-maneuver or lateral-maneuver replacement processes regardless of params. */
        :>> workProduct = "WP-S-07";
        :>> allocText = "SoC";
        :>> group = "CSR-C-07";
        :>> groupTitle = "Developer modes (CSG-03, CAL 2)";
        :>> safetyRelation = "TSR-613, QM (B-sup)";
        :>> verifMethod = "BA, UT";
        :>> status = "in";
    }
    requirement <'CSR-072'> csr_072 : CybersecurityRequirement {
        doc /* Driver-view demo mode (IsDriverViewEnabled) shall not affect driver-monitoring output while onroad. */
        :>> workProduct = "WP-S-07";
        :>> allocText = "SoC";
        :>> group = "CSR-C-07";
        :>> groupTitle = "Developer modes (CSG-03, CAL 2)";
        :>> safetyRelation = "TSR-610, QM";
        :>> verifMethod = "UT";
        :>> status = "in";
    }
    requirement <'CSR-073'> csr_073 : CybersecurityRequirement {
        doc /* The release build check shall fail if any developer-mode entry point is reachable in the release configuration. */
        :>> workProduct = "WP-S-07";
        :>> allocText = "ENV";
        :>> group = "CSR-C-07";
        :>> groupTitle = "Developer modes (CSG-03, CAL 2)";
        :>> safetyRelation = "—";
        :>> verifMethod = "BA";
        :>> status = "partly";
    }
    requirement <'CSR-081'> csr_081 : CybersecurityRequirement {
        doc /* modeld and dmonitoringmodeld shall load model artefacts and metadata without deserializing executable objects (no pickle of artefact content). */
        :>> workProduct = "WP-S-07";
        :>> allocText = "SoC";
        :>> group = "CSR-C-08";
        :>> groupTitle = "Model artefacts (CSG-04, CAL 2)";
        :>> safetyRelation = "AIR (WP-C-11); GAP-22";
        :>> verifMethod = "R, UT";
        :>> status = "not";
    }
    requirement <'CSR-082'> csr_082 : CybersecurityRequirement {
        doc /* Before loading, every model artefact shall be verified against a SHA-256 hash in the authenticated release manifest, and the process shall refuse to run on mismatch so that engagement is blocked. */
        :>> workProduct = "WP-S-07";
        :>> allocText = "SoC";
        :>> group = "CSR-C-08";
        :>> groupTitle = "Model artefacts (CSG-04, CAL 2)";
        :>> safetyRelation = "AIR; TSR-801 (model hashes at installation)";
        :>> verifMethod = "UT, HIL";
        :>> status = "not";
    }
    requirement <'CSR-083'> csr_083 : CybersecurityRequirement {
        doc /* Model artefacts shall be fetched from LionDriver-controlled storage and their hashes recorded in the release record. */
        :>> workProduct = "WP-S-07";
        :>> allocText = "ENV; USR";
        :>> group = "CSR-C-08";
        :>> groupTitle = "Model artefacts (CSG-04, CAL 2)";
        :>> safetyRelation = "D-05";
        :>> verifMethod = "CM";
        :>> status = "not";
    }
    requirement <'CSR-091'> csr_091 : CybersecurityRequirement {
        doc /* Panda firmware shall verify every checksum and counter that the vehicle provides on safety-relevant RX messages, and shall cross-check messages that carry none (brake 0x226, wheel speed 0xAA) for plausibility against independent signals. */
        :>> workProduct = "WP-S-07";
        :>> allocText = "FW";
        :>> group = "CSR-C-09";
        :>> groupTitle = "Vehicle CAN (CSG-05, CAL 2)";
        :>> safetyRelation = "TSR-401…405, B‡; GAP-01";
        :>> verifMethod = "R, UT, HIL";
        :>> status = "partly";
    }
    requirement <'CSR-092'> csr_092 : CybersecurityRequirement {
        doc /* Panda firmware shall transmit only allow-listed actuation messages on the car-side bus and shall not alter camera-originated PCS messages it forwards. */
        :>> workProduct = "WP-S-07";
        :>> allocText = "FW";
        :>> group = "CSR-C-09";
        :>> groupTitle = "Vehicle CAN (CSG-05, CAL 2)";
        :>> safetyRelation = "TSR-7xx, SG-07";
        :>> verifMethod = "R, UT";
        :>> status = "partly";
    }
    requirement <'CSR-093'> csr_093 : CybersecurityRequirement {
        doc /* Reception on the car-side bus of an actuation message ID that the panda transmits, while the relay intercepts, shall be detected and lead to actuation inhibit. */
        :>> workProduct = "WP-S-07";
        :>> allocText = "FW";
        :>> group = "CSR-C-09";
        :>> groupTitle = "Vehicle CAN (CSG-05, CAL 2)";
        :>> safetyRelation = "TSR-506, HWSR-506b, B‡";
        :>> verifMethod = "UT, HIL";
        :>> status = "partly";
    }
    requirement <'CSR-101'> csr_101 : CybersecurityRequirement {
        doc /* LionDriver installer and image builds shall not contain an embedded authorized SSH key or set SshEnabled. */
        :>> workProduct = "WP-S-07";
        :>> allocText = "SoC; ENV";
        :>> group = "CSR-C-10";
        :>> groupTitle = "SSH (CSG-06, CAL 3)";
        :>> safetyRelation = "—";
        :>> verifMethod = "BA";
        :>> status = "not";
    }
    requirement <'CSR-102'> csr_102 : CybersecurityRequirement {
        doc /* SshEnabled shall be false in the reference configuration and checked at installation. */
        :>> workProduct = "WP-S-07";
        :>> allocText = "USR";
        :>> group = "CSR-C-10";
        :>> groupTitle = "SSH (CSG-06, CAL 3)";
        :>> safetyRelation = "TSR-806";
        :>> verifMethod = "PR";
        :>> status = "in";
    }
    requirement <'CSR-103'> csr_103 : CybersecurityRequirement {
        doc /* When the owner enables SSH, only key authentication with owner-provided keys shall be accepted. */
        :>> workProduct = "WP-S-07";
        :>> allocText = "SoC";
        :>> group = "CSR-C-10";
        :>> groupTitle = "SSH (CSG-06, CAL 3)";
        :>> safetyRelation = "—";
        :>> verifMethod = "R, PT";
        :>> status = "check";
    }
    requirement <'CSR-104'> csr_104 : CybersecurityRequirement {
        doc /* SSH shall not accept new sessions while the vehicle is onroad. */
        :>> workProduct = "WP-S-07";
        :>> allocText = "SoC";
        :>> group = "CSR-C-10";
        :>> groupTitle = "SSH (CSG-06, CAL 3)";
        :>> safetyRelation = "—";
        :>> verifMethod = "HIL, PT";
        :>> status = "not";
    }
    requirement <'CSR-111'> csr_111 : CybersecurityRequirement {
        doc /* athenad shall not run in the reference configuration unless the owner opts in. */
        :>> workProduct = "WP-S-07";
        :>> allocText = "SoC; USR";
        :>> group = "CSR-C-11";
        :>> groupTitle = "Remote RPC (CSG-06, CAL 3)";
        :>> safetyRelation = "—";
        :>> verifMethod = "BA, PR";
        :>> status = "not";
    }
    requirement <'CSR-112'> csr_112 : CybersecurityRequirement {
        doc /* If enabled, file uploads requested over athena shall go only to allow-listed destination hosts over TLS with certificate validation. */
        :>> workProduct = "WP-S-07";
        :>> allocText = "SoC";
        :>> group = "CSR-C-11";
        :>> groupTitle = "Remote RPC (CSG-06, CAL 3)";
        :>> safetyRelation = "—";
        :>> verifMethod = "UT, PT";
        :>> status = "partly";
    }
    requirement <'CSR-113'> csr_113 : CybersecurityRequirement {
        doc /* If enabled, the SSH-tunnel and authorized-key RPCs shall be absent. */
        :>> workProduct = "WP-S-07";
        :>> allocText = "SoC";
        :>> group = "CSR-C-11";
        :>> groupTitle = "Remote RPC (CSG-06, CAL 3)";
        :>> safetyRelation = "—";
        :>> verifMethod = "UT, PT";
        :>> status = "not";
    }
    requirement <'CSR-114'> csr_114 : CybersecurityRequirement {
        doc /* If enabled, getMessage shall serve only allow-listed, non-personal services. */
        :>> workProduct = "WP-S-07";
        :>> allocText = "SoC";
        :>> group = "CSR-C-11";
        :>> groupTitle = "Remote RPC (CSG-06, CAL 3)";
        :>> safetyRelation = "—";
        :>> verifMethod = "UT";
        :>> status = "not";
    }
    requirement <'CSR-115'> csr_115 : CybersecurityRequirement {
        doc /* Release builds shall ignore the ATHENA_HOST environment override. */
        :>> workProduct = "WP-S-07";
        :>> allocText = "SoC";
        :>> group = "CSR-C-11";
        :>> groupTitle = "Remote RPC (CSG-06, CAL 3)";
        :>> safetyRelation = "—";
        :>> verifMethod = "BA, UT";
        :>> status = "not";
    }
    requirement <'CSR-116'> csr_116 : CybersecurityRequirement {
        doc /* Onroad camera streaming shall remain impossible, and webrtcd shall bind only to the loopback interface. */
        :>> workProduct = "WP-S-07";
        :>> allocText = "SoC";
        :>> group = "CSR-C-11";
        :>> groupTitle = "Remote RPC (CSG-06, CAL 3)";
        :>> safetyRelation = "—";
        :>> verifMethod = "UT, PT";
        :>> status = "in";
    }
    requirement <'CSR-117'> csr_117 : CybersecurityRequirement {
        doc /* No safety function shall depend on athena or any back-end availability. */
        :>> workProduct = "WP-S-07";
        :>> allocText = "SoC";
        :>> group = "CSR-C-11";
        :>> groupTitle = "Remote RPC (CSG-06, CAL 3)";
        :>> safetyRelation = "CA-01";
        :>> verifMethod = "HIL (network off)";
        :>> status = "check";
    }
    requirement <'CSR-121'> csr_121 : CybersecurityRequirement {
        doc /* The updater shall stage an update only after verifying a LionDriver-signed release manifest (§3.6) and every artefact against it; the manifest signature uses the firmware scheme, ECDSA over P-256 with SHA-256 (DQ-191 A), with the offline update key. */
        :>> workProduct = "WP-S-07";
        :>> allocText = "SoC; ENV";
        :>> group = "CSR-C-12";
        :>> groupTitle = "Software updates (CSG-07, CAL 3)";
        :>> safetyRelation = "TSR-810, TSR-801";
        :>> verifMethod = "R, UT, PT";
        :>> status = "not";
    }
    requirement <'CSR-122'> csr_122 : CybersecurityRequirement {
        doc /* Release builds shall fix the update origin and accept only release-channel branches, ignoring UpdaterTargetBranch values outside it. */
        :>> workProduct = "WP-S-07";
        :>> allocText = "SoC";
        :>> group = "CSR-C-12";
        :>> groupTitle = "Software updates (CSG-07, CAL 3)";
        :>> safetyRelation = "TSR-810";
        :>> verifMethod = "UT";
        :>> status = "not";
    }
    requirement <'CSR-123'> csr_123 : CybersecurityRequirement {
        doc /* The updater shall reject a manifest whose release version is lower than the installed one unless the manifest is a signed rollback release. */
        :>> workProduct = "WP-S-07";
        :>> allocText = "SoC; ENV";
        :>> group = "CSR-C-12";
        :>> groupTitle = "Software updates (CSG-07, CAL 3)";
        :>> safetyRelation = "—";
        :>> verifMethod = "UT";
        :>> status = "not";
    }
    requirement <'CSR-124'> csr_124 : CybersecurityRequirement {
        doc /* Until CSR-121 is implemented, DisableUpdates shall be set in the reference configuration and updates installed manually per WP-O-02 UPD-02. */
        :>> workProduct = "WP-S-07";
        :>> allocText = "USR";
        :>> group = "CSR-C-12";
        :>> groupTitle = "Software updates (CSG-07, CAL 3)";
        :>> safetyRelation = "TSR-810";
        :>> verifMethod = "PR";
        :>> status = "in";
    }
    requirement <'CSR-125'> csr_125 : CybersecurityRequirement {
        doc /* Update installation shall be offroad-only and atomic, with the previous release remaining bootable if finalization fails. */
        :>> workProduct = "WP-S-07";
        :>> allocText = "SoC";
        :>> group = "CSR-C-12";
        :>> groupTitle = "Software updates (CSG-07, CAL 3)";
        :>> safetyRelation = "UPD-05";
        :>> verifMethod = "R, HIL";
        :>> status = "partly";
    }
    requirement <'CSR-126'> csr_126 : CybersecurityRequirement {
        doc /* The update-signing key shall be distinct from the panda release key, held offline, and covered by a re-keying procedure. */
        :>> workProduct = "WP-S-07";
        :>> allocText = "ENV";
        :>> group = "CSR-C-12";
        :>> groupTitle = "Software updates (CSG-07, CAL 3)";
        :>> safetyRelation = "—";
        :>> verifMethod = "PR";
        :>> status = "not";
    }
    requirement <'CSR-131'> csr_131 : CybersecurityRequirement {
        doc /* All submodules shall point to LionDriver-controlled forks and be pinned by commit. */
        :>> workProduct = "WP-S-07";
        :>> allocText = "ENV";
        :>> group = "CSR-C-13";
        :>> groupTitle = "Supply chain (CSG-07, CAL 3)";
        :>> safetyRelation = "D-01";
        :>> verifMethod = "CM";
        :>> status = "not";
    }
    requirement <'CSR-132'> csr_132 : CybersecurityRequirement {
        doc /* No release dependency or tool shall be resolved from a mutable reference (branch or tag without hash). */
        :>> workProduct = "WP-S-07";
        :>> allocText = "ENV";
        :>> group = "CSR-C-13";
        :>> groupTitle = "Supply chain (CSG-07, CAL 3)";
        :>> safetyRelation = "GAP-34";
        :>> verifMethod = "CM, BA";
        :>> status = "not";
    }
    requirement <'CSR-133'> csr_133 : CybersecurityRequirement {
        doc /* Every release shall have an SBOM covering uv.lock packages, submodule commits, LFS artefacts, AGNOS version and images, comma-deps wheels and the panda toolchain. */
        :>> workProduct = "WP-S-07";
        :>> allocText = "ENV";
        :>> group = "CSR-C-13";
        :>> groupTitle = "Supply chain (CSG-07, CAL 3)";
        :>> safetyRelation = "—";
        :>> verifMethod = "CM";
        :>> status = "not";
    }
    requirement <'CSR-134'> csr_134 : CybersecurityRequirement {
        doc /* Every release and the current release weekly shall be scanned against public vulnerability data, with each finding assessed before release. */
        :>> workProduct = "WP-S-07";
        :>> allocText = "ENV";
        :>> group = "CSR-C-13";
        :>> groupTitle = "Supply chain (CSG-07, CAL 3)";
        :>> safetyRelation = "—";
        :>> verifMethod = "CM";
        :>> status = "not";
    }
    requirement <'CSR-135'> csr_135 : CybersecurityRequirement {
        doc /* Release signing material shall never be available to CI jobs triggered from pull requests or forks. */
        :>> workProduct = "WP-S-07";
        :>> allocText = "ENV";
        :>> group = "CSR-C-13";
        :>> groupTitle = "Supply chain (CSG-07, CAL 3)";
        :>> safetyRelation = "—";
        :>> verifMethod = "CM, R";
        :>> status = "not";
    }
    requirement <'CSR-141'> csr_141 : CybersecurityRequirement {
        doc /* The device identity private key shall be readable only by the processes that sign with it and shall not be exposed through any RPC, log or upload. */
        :>> workProduct = "WP-S-07";
        :>> allocText = "SoC";
        :>> group = "CSR-C-14";
        :>> groupTitle = "Personal data and identity key (CSG-08, CAL 2)";
        :>> safetyRelation = "—";
        :>> verifMethod = "R, PT";
        :>> status = "check";
    }
    requirement <'CSR-142'> csr_142 : CybersecurityRequirement {
        doc /* Driver-facing video, cabin imagery and location logs shall be encrypted at rest, or, if AGNOS cannot provide this, driver-camera recording shall be off by default and retention bounded. */
        :>> workProduct = "WP-S-07";
        :>> allocText = "SoC; USR";
        :>> group = "CSR-C-14";
        :>> groupTitle = "Personal data and identity key (CSG-08, CAL 2)";
        :>> safetyRelation = "—";
        :>> verifMethod = "R, HIL";
        :>> status = "check";
    }
    requirement <'CSR-143'> csr_143 : CybersecurityRequirement {
        doc /* Any data upload shall use TLS with certificate validation to an approved endpoint. */
        :>> workProduct = "WP-S-07";
        :>> allocText = "SoC; ENV";
        :>> group = "CSR-C-14";
        :>> groupTitle = "Personal data and identity key (CSG-08, CAL 2)";
        :>> safetyRelation = "—";
        :>> verifMethod = "R, PT";
        :>> status = "check";
    }
    requirement <'CSR-144'> csr_144 : CybersecurityRequirement {
        doc /* Driver-camera video shall not be uploaded unless the owner opts in. */
        :>> workProduct = "WP-S-07";
        :>> allocText = "SoC; USR";
        :>> group = "CSR-C-14";
        :>> groupTitle = "Personal data and identity key (CSG-08, CAL 2)";
        :>> safetyRelation = "—";
        :>> verifMethod = "R, PR";
        :>> status = "check";
    }
    requirement <'CSR-151'> csr_151 : CybersecurityRequirement {
        doc /* The decommissioning procedure shall erase user data and the device identity keys in /persist/comma/. */
        :>> workProduct = "WP-S-07";
        :>> allocText = "USR; SoC";
        :>> group = "CSR-C-15";
        :>> groupTitle = "Decommissioning (CSG-08, CAL 2)";
        :>> safetyRelation = "TSR-814";
        :>> verifMethod = "PR, HIL";
        :>> status = "partly";
    }
    requirement <'CSR-152'> csr_152 : CybersecurityRequirement {
        doc /* Decommissioning shall revoke the device's credentials at every LionDriver endpoint and remove owner SSH keys. */
        :>> workProduct = "WP-S-07";
        :>> allocText = "USR; ENV";
        :>> group = "CSR-C-15";
        :>> groupTitle = "Decommissioning (CSG-08, CAL 2)";
        :>> safetyRelation = "TSR-814";
        :>> verifMethod = "PR";
        :>> status = "partly";
    }
    requirement <'CSR-161'> csr_161 : CybersecurityRequirement {
        doc /* LionDriver shall publish a security policy with a private reporting channel it controls. */
        :>> workProduct = "WP-S-07";
        :>> allocText = "USR; ENV";
        :>> group = "CSR-C-16";
        :>> groupTitle = "Vulnerability handling (CAL 1)";
        :>> safetyRelation = "—";
        :>> verifMethod = "PR";
        :>> status = "not";
    }
    requirement <'CSR-162'> csr_162 : CybersecurityRequirement {
        doc /* Vulnerability analysis, incident response and update management shall run per WP-O-05 from G6. */
        :>> workProduct = "WP-S-07";
        :>> allocText = "USR";
        :>> group = "CSR-C-16";
        :>> groupTitle = "Vulnerability handling (CAL 1)";
        :>> safetyRelation = "WP-O-04 field actions";
        :>> verifMethod = "PR";
        :>> status = "not";
    }

    // derivation: each requirement from its parents in the trace data
    #derivation connection {
        end #original ::> sg_01;
        end #derive ::> fsr_01_01;
    }
    #derivation connection {
        end #original ::> sg_01;
        end #derive ::> fsr_01_02;
    }
    #derivation connection {
        end #original ::> sg_01;
        end #derive ::> fsr_01_03;
    }
    #derivation connection {
        end #original ::> sg_01;
        end #derive ::> fsr_01_04;
    }
    #derivation connection {
        end #original ::> sg_01;
        end #derive ::> fsr_01_05;
    }
    #derivation connection {
        end #original ::> sg_03;
        end #derive ::> fsr_01_05;
    }
    #derivation connection {
        end #original ::> sg_04;
        end #derive ::> fsr_01_05;
    }
    #derivation connection {
        end #original ::> sg_05;
        end #derive ::> fsr_01_05;
    }
    #derivation connection {
        end #original ::> sg_01;
        end #derive ::> fsr_01_06;
    }
    #derivation connection {
        end #original ::> sg_03;
        end #derive ::> fsr_01_06;
    }
    #derivation connection {
        end #original ::> sg_04;
        end #derive ::> fsr_01_06;
    }
    #derivation connection {
        end #original ::> sg_05;
        end #derive ::> fsr_01_06;
    }
    #derivation connection {
        end #original ::> sg_01;
        end #derive ::> fsr_01_07;
    }
    #derivation connection {
        end #original ::> sg_02;
        end #derive ::> fsr_01_07;
    }
    #derivation connection {
        end #original ::> sg_03;
        end #derive ::> fsr_01_07;
    }
    #derivation connection {
        end #original ::> sg_04;
        end #derive ::> fsr_01_07;
    }
    #derivation connection {
        end #original ::> sg_06;
        end #derive ::> fsr_01_07;
    }
    #derivation connection {
        end #original ::> sg_01;
        end #derive ::> fsr_01_08;
    }
    #derivation connection {
        end #original ::> sg_03;
        end #derive ::> fsr_01_08;
    }
    #derivation connection {
        end #original ::> sg_04;
        end #derive ::> fsr_01_08;
    }
    #derivation connection {
        end #original ::> sg_01;
        end #derive ::> fsr_01_09;
    }
    #derivation connection {
        end #original ::> sg_02;
        end #derive ::> fsr_01_09;
    }
    #derivation connection {
        end #original ::> sg_03;
        end #derive ::> fsr_01_09;
    }
    #derivation connection {
        end #original ::> sg_04;
        end #derive ::> fsr_01_09;
    }
    #derivation connection {
        end #original ::> sg_05;
        end #derive ::> fsr_01_09;
    }
    #derivation connection {
        end #original ::> sg_06;
        end #derive ::> fsr_01_09;
    }
    #derivation connection {
        end #original ::> sg_07;
        end #derive ::> fsr_01_09;
    }
    #derivation connection {
        end #original ::> sg_01;
        end #derive ::> fsr_01_10;
    }
    #derivation connection {
        end #original ::> sg_03;
        end #derive ::> fsr_01_10;
    }
    #derivation connection {
        end #original ::> sg_04;
        end #derive ::> fsr_01_10;
    }
    #derivation connection {
        end #original ::> sg_05;
        end #derive ::> fsr_01_10;
    }
    #derivation connection {
        end #original ::> sg_07;
        end #derive ::> fsr_01_10;
    }
    #derivation connection {
        end #original ::> sg_01;
        end #derive ::> fsr_01_11;
    }
    #derivation connection {
        end #original ::> sg_03;
        end #derive ::> fsr_01_11;
    }
    #derivation connection {
        end #original ::> sg_07;
        end #derive ::> fsr_01_11;
    }
    #derivation connection {
        end #original ::> sg_01;
        end #derive ::> fsr_01_12;
    }
    #derivation connection {
        end #original ::> sg_01;
        end #derive ::> fsr_01_13;
    }
    #derivation connection {
        end #original ::> sg_05;
        end #derive ::> fsr_01_13;
    }
    #derivation connection {
        end #original ::> sg_01;
        end #derive ::> fsr_01_14;
    }
    #derivation connection {
        end #original ::> sg_02;
        end #derive ::> fsr_02_01;
    }
    #derivation connection {
        end #original ::> sg_02;
        end #derive ::> fsr_02_02;
    }
    #derivation connection {
        end #original ::> sg_02;
        end #derive ::> fsr_02_03;
    }
    #derivation connection {
        end #original ::> sg_02;
        end #derive ::> fsr_02_04;
    }
    #derivation connection {
        end #original ::> sg_02;
        end #derive ::> fsr_02_05;
    }
    #derivation connection {
        end #original ::> sg_02;
        end #derive ::> fsr_02_06;
    }
    #derivation connection {
        end #original ::> sg_06;
        end #derive ::> fsr_02_06;
    }
    #derivation connection {
        end #original ::> sg_08;
        end #derive ::> fsr_02_06;
    }
    #derivation connection {
        end #original ::> sg_02;
        end #derive ::> fsr_02_07;
    }
    #derivation connection {
        end #original ::> sg_06;
        end #derive ::> fsr_02_07;
    }
    #derivation connection {
        end #original ::> sg_08;
        end #derive ::> fsr_02_07;
    }
    #derivation connection {
        end #original ::> sg_02;
        end #derive ::> fsr_02_08;
    }
    #derivation connection {
        end #original ::> sg_06;
        end #derive ::> fsr_02_08;
    }
    #derivation connection {
        end #original ::> sg_08;
        end #derive ::> fsr_02_08;
    }
    #derivation connection {
        end #original ::> sg_02;
        end #derive ::> fsr_02_09;
    }
    #derivation connection {
        end #original ::> sg_04;
        end #derive ::> fsr_02_09;
    }
    #derivation connection {
        end #original ::> sg_06;
        end #derive ::> fsr_02_09;
    }
    #derivation connection {
        end #original ::> sg_08;
        end #derive ::> fsr_02_09;
    }
    #derivation connection {
        end #original ::> sg_02;
        end #derive ::> fsr_02_10;
    }
    #derivation connection {
        end #original ::> sg_06;
        end #derive ::> fsr_02_10;
    }
    #derivation connection {
        end #original ::> sg_02;
        end #derive ::> fsr_02_11;
    }
    #derivation connection {
        end #original ::> sg_06;
        end #derive ::> fsr_02_11;
    }
    #derivation connection {
        end #original ::> sg_02;
        end #derive ::> fsr_02_12;
    }
    #derivation connection {
        end #original ::> sg_06;
        end #derive ::> fsr_02_12;
    }
    #derivation connection {
        end #original ::> sg_03;
        end #derive ::> fsr_03_01;
    }
    #derivation connection {
        end #original ::> sg_03;
        end #derive ::> fsr_03_02;
    }
    #derivation connection {
        end #original ::> sg_04;
        end #derive ::> fsr_03_02;
    }
    #derivation connection {
        end #original ::> sg_03;
        end #derive ::> fsr_03_03;
    }
    #derivation connection {
        end #original ::> sg_03;
        end #derive ::> fsr_03_04;
    }
    #derivation connection {
        end #original ::> sg_03;
        end #derive ::> fsr_03_05;
    }
    #derivation connection {
        end #original ::> sg_03;
        end #derive ::> fsr_03_06;
    }
    #derivation connection {
        end #original ::> sg_04;
        end #derive ::> fsr_04_01;
    }
    #derivation connection {
        end #original ::> sg_04;
        end #derive ::> fsr_04_02;
    }
    #derivation connection {
        end #original ::> sg_04;
        end #derive ::> fsr_04_03;
    }
    #derivation connection {
        end #original ::> sg_04;
        end #derive ::> fsr_04_04;
    }
    #derivation connection {
        end #original ::> sg_04;
        end #derive ::> fsr_04_05;
    }
    #derivation connection {
        end #original ::> sg_04;
        end #derive ::> fsr_04_06;
    }
    #derivation connection {
        end #original ::> sg_05;
        end #derive ::> fsr_05_01;
    }
    #derivation connection {
        end #original ::> sg_05;
        end #derive ::> fsr_05_02;
    }
    #derivation connection {
        end #original ::> sg_05;
        end #derive ::> fsr_05_03;
    }
    #derivation connection {
        end #original ::> sg_05;
        end #derive ::> fsr_05_04;
    }
    #derivation connection {
        end #original ::> sg_02;
        end #derive ::> fsr_05_05;
    }
    #derivation connection {
        end #original ::> sg_05;
        end #derive ::> fsr_05_05;
    }
    #derivation connection {
        end #original ::> sg_06;
        end #derive ::> fsr_05_05;
    }
    #derivation connection {
        end #original ::> sg_02;
        end #derive ::> fsr_05_06;
    }
    #derivation connection {
        end #original ::> sg_05;
        end #derive ::> fsr_05_06;
    }
    #derivation connection {
        end #original ::> sg_06;
        end #derive ::> fsr_05_06;
    }
    #derivation connection {
        end #original ::> sg_05;
        end #derive ::> fsr_05_07;
    }
    #derivation connection {
        end #original ::> sg_06;
        end #derive ::> fsr_06_01;
    }
    #derivation connection {
        end #original ::> sg_06;
        end #derive ::> fsr_06_02;
    }
    #derivation connection {
        end #original ::> sg_06;
        end #derive ::> fsr_06_03;
    }
    #derivation connection {
        end #original ::> sg_06;
        end #derive ::> fsr_06_04;
    }
    #derivation connection {
        end #original ::> sg_06;
        end #derive ::> fsr_06_05;
    }
    #derivation connection {
        end #original ::> sg_07;
        end #derive ::> fsr_07_01;
    }
    #derivation connection {
        end #original ::> sg_07;
        end #derive ::> fsr_07_02;
    }
    #derivation connection {
        end #original ::> sg_07;
        end #derive ::> fsr_07_03;
    }
    #derivation connection {
        end #original ::> sg_07;
        end #derive ::> fsr_07_04;
    }
    #derivation connection {
        end #original ::> sg_07;
        end #derive ::> fsr_07_05;
    }
    #derivation connection {
        end #original ::> sg_07;
        end #derive ::> fsr_07_06;
    }
    #derivation connection {
        end #original ::> sg_07;
        end #derive ::> fsr_07_07;
    }
    #derivation connection {
        end #original ::> sg_08;
        end #derive ::> fsr_08_01;
    }
    #derivation connection {
        end #original ::> fsr_01_01;
        end #derive ::> tsr_101;
    }
    #derivation connection {
        end #original ::> fsr_01_01;
        end #derive ::> tsr_102;
    }
    #derivation connection {
        end #original ::> fsr_01_02;
        end #derive ::> tsr_103;
    }
    #derivation connection {
        end #original ::> fsr_01_03;
        end #derive ::> tsr_104;
    }
    #derivation connection {
        end #original ::> fsr_01_04;
        end #derive ::> tsr_105;
    }
    #derivation connection {
        end #original ::> fsr_01_04;
        end #derive ::> tsr_106;
    }
    #derivation connection {
        end #original ::> fsr_01_04;
        end #derive ::> tsr_107;
    }
    #derivation connection {
        end #original ::> fsr_01_12;
        end #derive ::> tsr_108;
    }
    #derivation connection {
        end #original ::> fsr_01_12;
        end #derive ::> tsr_109;
    }
    #derivation connection {
        end #original ::> fsr_01_13;
        end #derive ::> tsr_109;
    }
    #derivation connection {
        end #original ::> fsr_05_01;
        end #derive ::> tsr_109;
    }
    #derivation connection {
        end #original ::> fsr_02_04;
        end #derive ::> tsr_109;
    }
    #derivation connection {
        end #original ::> fsr_02_01;
        end #derive ::> tsr_110;
    }
    #derivation connection {
        end #original ::> fsr_01_13;
        end #derive ::> tsr_111;
    }
    #derivation connection {
        end #original ::> fsr_03_01;
        end #derive ::> tsr_201;
    }
    #derivation connection {
        end #original ::> fsr_04_01;
        end #derive ::> tsr_202;
    }
    #derivation connection {
        end #original ::> fsr_03_02;
        end #derive ::> tsr_203;
    }
    #derivation connection {
        end #original ::> fsr_04_04;
        end #derive ::> tsr_203;
    }
    #derivation connection {
        end #original ::> fsr_05_04;
        end #derive ::> tsr_203;
    }
    #derivation connection {
        end #original ::> fsr_03_03;
        end #derive ::> tsr_204;
    }
    #derivation connection {
        end #original ::> fsr_04_02;
        end #derive ::> tsr_205;
    }
    #derivation connection {
        end #original ::> fsr_03_05;
        end #derive ::> tsr_206;
    }
    #derivation connection {
        end #original ::> fsr_04_03;
        end #derive ::> tsr_206;
    }
    #derivation connection {
        end #original ::> fsr_03_02;
        end #derive ::> tsr_207;
    }
    #derivation connection {
        end #original ::> fsr_03_05;
        end #derive ::> tsr_207;
    }
    #derivation connection {
        end #original ::> fsr_03_06;
        end #derive ::> tsr_208;
    }
    #derivation connection {
        end #original ::> fsr_04_03;
        end #derive ::> tsr_208;
    }
    #derivation connection {
        end #original ::> fsr_01_05;
        end #derive ::> tsr_301;
    }
    #derivation connection {
        end #original ::> fsr_05_02;
        end #derive ::> tsr_301;
    }
    #derivation connection {
        end #original ::> fsr_05_01;
        end #derive ::> tsr_302;
    }
    #derivation connection {
        end #original ::> fsr_03_05;
        end #derive ::> tsr_303;
    }
    #derivation connection {
        end #original ::> fsr_02_03;
        end #derive ::> tsr_303;
    }
    #derivation connection {
        end #original ::> fsr_06_02;
        end #derive ::> tsr_303;
    }
    #derivation connection {
        end #original ::> fsr_05_03;
        end #derive ::> tsr_304;
    }
    #derivation connection {
        end #original ::> fsr_04_04;
        end #derive ::> tsr_305;
    }
    #derivation connection {
        end #original ::> fsr_05_04;
        end #derive ::> tsr_305;
    }
    #derivation connection {
        end #original ::> fsr_01_05;
        end #derive ::> tsr_306;
    }
    #derivation connection {
        end #original ::> fsr_01_06;
        end #derive ::> tsr_306;
    }
    #derivation connection {
        end #original ::> fsr_05_06;
        end #derive ::> tsr_307;
    }
    #derivation connection {
        end #original ::> fsr_01_07;
        end #derive ::> tsr_307;
    }
    #derivation connection {
        end #original ::> fsr_05_06;
        end #derive ::> tsr_308;
    }
    #derivation connection {
        end #original ::> fsr_05_05;
        end #derive ::> tsr_309;
    }
    #derivation connection {
        end #original ::> fsr_05_07;
        end #derive ::> tsr_310;
    }
    #derivation connection {
        end #original ::> fsr_01_05;
        end #derive ::> tsr_311;
    }
    #derivation connection {
        end #original ::> fsr_01_06;
        end #derive ::> tsr_401;
    }
    #derivation connection {
        end #original ::> fsr_01_06;
        end #derive ::> tsr_402;
    }
    #derivation connection {
        end #original ::> fsr_01_06;
        end #derive ::> tsr_403;
    }
    #derivation connection {
        end #original ::> fsr_01_06;
        end #derive ::> tsr_404;
    }
    #derivation connection {
        end #original ::> fsr_01_06;
        end #derive ::> tsr_405;
    }
    #derivation connection {
        end #original ::> fsr_05_01;
        end #derive ::> tsr_405;
    }
    #derivation connection {
        end #original ::> fsr_01_06;
        end #derive ::> tsr_406;
    }
    #derivation connection {
        end #original ::> fsr_01_12;
        end #derive ::> tsr_406;
    }
    #derivation connection {
        end #original ::> fsr_01_07;
        end #derive ::> tsr_407;
    }
    #derivation connection {
        end #original ::> fsr_01_07;
        end #derive ::> tsr_408;
    }
    #derivation connection {
        end #original ::> fsr_01_07;
        end #derive ::> tsr_409;
    }
    #derivation connection {
        end #original ::> fsr_01_08;
        end #derive ::> tsr_410;
    }
    #derivation connection {
        end #original ::> fsr_01_08;
        end #derive ::> tsr_411;
    }
    #derivation connection {
        end #original ::> fsr_01_08;
        end #derive ::> tsr_412;
    }
    #derivation connection {
        end #original ::> fsr_01_10;
        end #derive ::> tsr_412;
    }
    #derivation connection {
        end #original ::> fsr_01_08;
        end #derive ::> tsr_413;
    }
    #derivation connection {
        end #original ::> fsr_01_09;
        end #derive ::> tsr_501;
    }
    #derivation connection {
        end #original ::> fsr_01_09;
        end #derive ::> tsr_502;
    }
    #derivation connection {
        end #original ::> fsr_07_03;
        end #derive ::> tsr_502;
    }
    #derivation connection {
        end #original ::> fsr_01_09;
        end #derive ::> tsr_503;
    }
    #derivation connection {
        end #original ::> fsr_01_09;
        end #derive ::> tsr_504;
    }
    #derivation connection {
        end #original ::> fsr_01_09;
        end #derive ::> tsr_505;
    }
    #derivation connection {
        end #original ::> fsr_01_11;
        end #derive ::> tsr_506;
    }
    #derivation connection {
        end #original ::> fsr_07_03;
        end #derive ::> tsr_506;
    }
    #derivation connection {
        end #original ::> fsr_01_09;
        end #derive ::> tsr_507;
    }
    #derivation connection {
        end #original ::> fsr_01_10;
        end #derive ::> tsr_507;
    }
    #derivation connection {
        end #original ::> fsr_01_09;
        end #derive ::> tsr_508;
    }
    #derivation connection {
        end #original ::> fsr_01_12;
        end #derive ::> tsr_508;
    }
    #derivation connection {
        end #original ::> fsr_01_09;
        end #derive ::> tsr_509;
    }
    #derivation connection {
        end #original ::> fsr_07_03;
        end #derive ::> tsr_510;
    }
    #derivation connection {
        end #original ::> fsr_01_10;
        end #derive ::> tsr_511;
    }
    #derivation connection {
        end #original ::> fsr_01_10;
        end #derive ::> tsr_512;
    }
    #derivation connection {
        end #original ::> fsr_01_10;
        end #derive ::> tsr_513;
    }
    #derivation connection {
        end #original ::> fsr_01_10;
        end #derive ::> tsr_514;
    }
    #derivation connection {
        end #original ::> fsr_01_09;
        end #derive ::> tsr_515;
    }
    #derivation connection {
        end #original ::> fsr_01_11;
        end #derive ::> tsr_515;
    }
    #derivation connection {
        end #original ::> fsr_02_05;
        end #derive ::> tsr_515;
    }
    #derivation connection {
        end #original ::> fsr_02_05;
        end #derive ::> tsr_516;
    }
    #derivation connection {
        end #original ::> fsr_06_05;
        end #derive ::> tsr_516;
    }
    #derivation connection {
        end #original ::> fsr_01_09;
        end #derive ::> tsr_517;
    }
    #derivation connection {
        end #original ::> fsr_01_08;
        end #derive ::> tsr_518;
    }
    #derivation connection {
        end #original ::> fsr_01_12;
        end #derive ::> tsr_518;
    }
    #derivation connection {
        end #original ::> fsr_01_09;
        end #derive ::> tsr_519;
    }
    #derivation connection {
        end #original ::> fsr_01_07;
        end #derive ::> tsr_519;
    }
    #derivation connection {
        end #original ::> fsr_02_02;
        end #derive ::> tsr_601;
    }
    #derivation connection {
        end #original ::> fsr_02_04;
        end #derive ::> tsr_601;
    }
    #derivation connection {
        end #original ::> fsr_06_02;
        end #derive ::> tsr_601;
    }
    #derivation connection {
        end #original ::> fsr_02_02;
        end #derive ::> tsr_602;
    }
    #derivation connection {
        end #original ::> fsr_06_01;
        end #derive ::> tsr_602;
    }
    #derivation connection {
        end #original ::> fsr_02_02;
        end #derive ::> tsr_603;
    }
    #derivation connection {
        end #original ::> fsr_06_01;
        end #derive ::> tsr_603;
    }
    #derivation connection {
        end #original ::> fsr_06_04;
        end #derive ::> tsr_604;
    }
    #derivation connection {
        end #original ::> fsr_01_14;
        end #derive ::> tsr_605;
    }
    #derivation connection {
        end #original ::> fsr_02_03;
        end #derive ::> tsr_606;
    }
    #derivation connection {
        end #original ::> fsr_06_02;
        end #derive ::> tsr_606;
    }
    #derivation connection {
        end #original ::> fsr_02_01;
        end #derive ::> tsr_607;
    }
    #derivation connection {
        end #original ::> fsr_02_06;
        end #derive ::> tsr_608;
    }
    #derivation connection {
        end #original ::> fsr_02_07;
        end #derive ::> tsr_609;
    }
    #derivation connection {
        end #original ::> fsr_02_08;
        end #derive ::> tsr_610;
    }
    #derivation connection {
        end #original ::> fsr_02_09;
        end #derive ::> tsr_611;
    }
    #derivation connection {
        end #original ::> fsr_02_07;
        end #derive ::> tsr_612;
    }
    #derivation connection {
        end #original ::> fsr_02_08;
        end #derive ::> tsr_613;
    }
    #derivation connection {
        end #original ::> fsr_01_14;
        end #derive ::> tsr_613;
    }
    #derivation connection {
        end #original ::> fsr_01_08;
        end #derive ::> tsr_614;
    }
    #derivation connection {
        end #original ::> fsr_01_12;
        end #derive ::> tsr_615;
    }
    #derivation connection {
        end #original ::> fsr_02_03;
        end #derive ::> tsr_615;
    }
    #derivation connection {
        end #original ::> fsr_02_02;
        end #derive ::> tsr_616;
    }
    #derivation connection {
        end #original ::> fsr_06_01;
        end #derive ::> tsr_616;
    }
    #derivation connection {
        end #original ::> fsr_01_14;
        end #derive ::> tsr_617;
    }
    #derivation connection {
        end #original ::> fsr_06_04;
        end #derive ::> tsr_617;
    }
    #derivation connection {
        end #original ::> fsr_06_03;
        end #derive ::> tsr_618;
    }
    #derivation connection {
        end #original ::> fsr_01_10;
        end #derive ::> tsr_619;
    }
    #derivation connection {
        end #original ::> fsr_01_10;
        end #derive ::> tsr_620;
    }
    #derivation connection {
        end #original ::> fsr_02_10;
        end #derive ::> tsr_621;
    }
    #derivation connection {
        end #original ::> fsr_02_11;
        end #derive ::> tsr_622;
    }
    #derivation connection {
        end #original ::> fsr_02_11;
        end #derive ::> tsr_623;
    }
    #derivation connection {
        end #original ::> fsr_04_05;
        end #derive ::> tsr_624;
    }
    #derivation connection {
        end #original ::> fsr_04_06;
        end #derive ::> tsr_625;
    }
    #derivation connection {
        end #original ::> fsr_02_10;
        end #derive ::> tsr_626;
    }
    #derivation connection {
        end #original ::> fsr_02_11;
        end #derive ::> tsr_627;
    }
    #derivation connection {
        end #original ::> fsr_02_03;
        end #derive ::> tsr_627;
    }
    #derivation connection {
        end #original ::> fsr_05_03;
        end #derive ::> tsr_628;
    }
    #derivation connection {
        end #original ::> fsr_02_12;
        end #derive ::> tsr_629;
    }
    #derivation connection {
        end #original ::> fsr_01_05;
        end #derive ::> tsr_630;
    }
    #derivation connection {
        end #original ::> fsr_02_10;
        end #derive ::> tsr_630;
    }
    #derivation connection {
        end #original ::> fsr_02_02;
        end #derive ::> tsr_631;
    }
    #derivation connection {
        end #original ::> fsr_06_01;
        end #derive ::> tsr_631;
    }
    #derivation connection {
        end #original ::> fsr_02_10;
        end #derive ::> tsr_632;
    }
    #derivation connection {
        end #original ::> fsr_02_09;
        end #derive ::> tsr_633;
    }
    #derivation connection {
        end #original ::> fsr_02_06;
        end #derive ::> tsr_634;
    }
    #derivation connection {
        end #original ::> fsr_08_01;
        end #derive ::> tsr_635;
    }
    #derivation connection {
        end #original ::> fsr_07_03;
        end #derive ::> tsr_701;
    }
    #derivation connection {
        end #original ::> fsr_07_03;
        end #derive ::> tsr_702;
    }
    #derivation connection {
        end #original ::> fsr_07_03;
        end #derive ::> tsr_703;
    }
    #derivation connection {
        end #original ::> fsr_07_01;
        end #derive ::> tsr_704;
    }
    #derivation connection {
        end #original ::> fsr_07_02;
        end #derive ::> tsr_705;
    }
    #derivation connection {
        end #original ::> fsr_07_03;
        end #derive ::> tsr_706;
    }
    #derivation connection {
        end #original ::> fsr_07_01;
        end #derive ::> tsr_707;
    }
    #derivation connection {
        end #original ::> fsr_07_04;
        end #derive ::> tsr_708;
    }
    #derivation connection {
        end #original ::> fsr_07_05;
        end #derive ::> tsr_709;
    }
    #derivation connection {
        end #original ::> fsr_01_11;
        end #derive ::> tsr_710;
    }
    #derivation connection {
        end #original ::> fsr_07_01;
        end #derive ::> tsr_711;
    }
    #derivation connection {
        end #original ::> fsr_07_03;
        end #derive ::> tsr_711;
    }
    #derivation connection {
        end #original ::> fsr_07_06;
        end #derive ::> tsr_712;
    }
    #derivation connection {
        end #original ::> fsr_07_07;
        end #derive ::> tsr_713;
    }
    #derivation connection {
        end #original ::> sg_01;
        end #derive ::> tsr_801;
    }
    #derivation connection {
        end #original ::> sg_02;
        end #derive ::> tsr_801;
    }
    #derivation connection {
        end #original ::> sg_03;
        end #derive ::> tsr_801;
    }
    #derivation connection {
        end #original ::> sg_04;
        end #derive ::> tsr_801;
    }
    #derivation connection {
        end #original ::> sg_05;
        end #derive ::> tsr_801;
    }
    #derivation connection {
        end #original ::> sg_06;
        end #derive ::> tsr_801;
    }
    #derivation connection {
        end #original ::> sg_07;
        end #derive ::> tsr_801;
    }
    #derivation connection {
        end #original ::> fsr_01_10;
        end #derive ::> tsr_802;
    }
    #derivation connection {
        end #original ::> tsr_511;
        end #derive ::> tsr_802;
    }
    #derivation connection {
        end #original ::> tsr_514;
        end #derive ::> tsr_802;
    }
    #derivation connection {
        end #original ::> fsr_01_10;
        end #derive ::> tsr_804;
    }
    #derivation connection {
        end #original ::> tsr_512;
        end #derive ::> tsr_804;
    }
    #derivation connection {
        end #original ::> fsr_07_01;
        end #derive ::> tsr_805;
    }
    #derivation connection {
        end #original ::> fsr_07_03;
        end #derive ::> tsr_805;
    }
    #derivation connection {
        end #original ::> tsr_704;
        end #derive ::> tsr_805;
    }
    #derivation connection {
        end #original ::> tsr_706;
        end #derive ::> tsr_805;
    }
    #derivation connection {
        end #original ::> fsr_02_08;
        end #derive ::> tsr_806;
    }
    #derivation connection {
        end #original ::> tsr_610;
        end #derive ::> tsr_806;
    }
    #derivation connection {
        end #original ::> tsr_613;
        end #derive ::> tsr_806;
    }
    #derivation connection {
        end #original ::> sg_07;
        end #derive ::> tsr_809;
    }
    #derivation connection {
        end #original ::> fsr_01_10;
        end #derive ::> tsr_810;
    }
    #derivation connection {
        end #original ::> sg_01;
        end #derive ::> tsr_813;
    }
    #derivation connection {
        end #original ::> sg_02;
        end #derive ::> tsr_813;
    }
    #derivation connection {
        end #original ::> sg_03;
        end #derive ::> tsr_813;
    }
    #derivation connection {
        end #original ::> sg_04;
        end #derive ::> tsr_813;
    }
    #derivation connection {
        end #original ::> sg_05;
        end #derive ::> tsr_813;
    }
    #derivation connection {
        end #original ::> sg_06;
        end #derive ::> tsr_813;
    }
    #derivation connection {
        end #original ::> sg_07;
        end #derive ::> tsr_813;
    }
    #derivation connection {
        end #original ::> sg_07;
        end #derive ::> tsr_814;
    }
}
