// GENERATED by assurance/models/sysml/tools/gen_timing_hsi.py from the work products. Do not edit;
// change the work product and regenerate (README §7).

package LionDriverSignals {
    doc /* The safety-relevant signals of WP-S-05 §11 that cross the hardware-software interfaces and the item
           boundary, one item each, with the elements that own them, the TSRs they serve and the cases that test
           them. */

    private import ScalarValues::*;

    item def Signal {
        doc /* A signal across an HSI or the item boundary (WP-S-05 §11). */
        attribute group : String;
        attribute hsi : String[0..*];
        attribute direction : String;
        attribute ownerText : String;
        attribute owners : String[0..*];
        attribute dataType : String;
        attribute valueRange : String;
        attribute integrity : String;
        attribute validity : String;
        attribute rate : String;
        attribute reaction : String;
        attribute tsrText : String;
        attribute tsr : String[0..*];
        attribute asil : String;
        attribute tests : String[0..*];
    }

    item <'S-01'> s_01 : Signal {
        doc /* STEER_REQUEST, 0x2E4 STEERING_LKA bit 0 */
        :>> group = "Vehicle CAN signals";
        :>> hsi = ("HSI-04");
        :>> direction = "MCU → EPS (TX, bus 0)";
        :>> ownerText = "SW: E-03a envelope (modes/toyota.h) checks; host card packs";
        :>> owners = ("E-03a", "host.card");
        :>> dataType = "bool, 1 bit";
        :>> valueRange = "0 / 1";
        :>> integrity = "8-bit CHECKSUM (byte 4)";
        :>> validity = "6-bit COUNTER (checked by the EPS, not by the item)";
        :>> rate = "100 Hz (host, every control frame, carcontroller.py:130-134)";
        :>> reaction = "Frame rejected by the envelope → SS-L, authority revoked (TSR-108, 109)";
        :>> tsrText = "105, 108, 109";
        :>> tsr = ("TSR-105", "TSR-108", "TSR-109");
        :>> asil = "B‡";
        :>> tests = ("VS-SI-15", "VS-FI-14");
    }
    item <'S-02'> s_02 : Signal {
        doc /* STEER_TORQUE_CMD, 0x2E4 */
        :>> group = "Vehicle CAN signals";
        :>> hsi = ("HSI-04");
        :>> direction = "MCU → EPS";
        :>> ownerText = "SW: E-03a envelope (modes/toyota.h) checks; host card packs";
        :>> owners = ("E-03a", "host.card");
        :>> dataType = "int16, signed";
        :>> valueRange = "raw, |cmd| ≤ 1500; Δ ≤ 15 up / 25 down per frame; ≤ 350 above measured EPS torque (toyota.h:173-177)";
        :>> integrity = "as S-01";
        :>> validity = "as S-01";
        :>> rate = "as S-01";
        :>> reaction = "as S-01";
        :>> tsrText = "101…104, 108, 109";
        :>> tsr = ("TSR-101", "TSR-102", "TSR-103", "TSR-104", "TSR-108", "TSR-109");
        :>> asil = "B‡";
        :>> tests = ("VS-SI-15", "VS-FI-14");
    }
    item <'S-03'> s_03 : Signal {
        doc /* ACCEL_CMD, 0x343 ACC_CONTROL */
        :>> group = "Vehicle CAN signals";
        :>> hsi = ("HSI-04");
        :>> direction = "MCU → PCM";
        :>> ownerText = "SW: E-03a envelope (modes/toyota.h) checks; host card packs";
        :>> owners = ("E-03a", "host.card");
        :>> dataType = "int16, signed";
        :>> valueRange = "0.001 m/s² per bit; −3.5 … +2.0 m/s² (toyota.h:208-209); inactive value 0";
        :>> integrity = "8-bit CHECKSUM (byte 7)";
        :>> validity = "none";
        :>> rate = "33 Hz (host, every third frame)";
        :>> reaction = "Frame rejected → inactive value; authority revoked on violation (TSR-108 analogue for longitudinal, TSR-203)";
        :>> tsrText = "201…207";
        :>> tsr = ("TSR-201", "TSR-202", "TSR-203", "TSR-204", "TSR-205", "TSR-206", "TSR-207");
        :>> asil = "B‡";
        :>> tests = ("VS-SI-16", "VS-FI-14");
    }
    item <'S-04'> s_04 : Signal {
        doc /* CANCEL_REQ, 0x343 bit 24 */
        :>> group = "Vehicle CAN signals";
        :>> hsi = ("HSI-04");
        :>> direction = "MCU → PCM";
        :>> ownerText = "SW: host controlsd/card (E-01)";
        :>> owners = ("E-01", "host.controlsd", "host.card");
        :>> dataType = "bool";
        :>> valueRange = "0 / 1";
        :>> integrity = "as S-03";
        :>> validity = "none";
        :>> rate = "with S-03";
        :>> reaction = "Cancel without effect → siren (TSR-516(c))";
        :>> tsrText = "303";
        :>> tsr = ("TSR-303");
        :>> asil = "QM (B-sup)";
        :>> tests = ("VS-SI-02", "VS-SI-24");
    }
    item <'S-05'> s_05 : Signal {
        doc /* LKAS_HUD 0x412 (cluster lane and alert display) */
        :>> group = "Vehicle CAN signals";
        :>> hsi = ("HSI-04");
        :>> direction = "MCU → cluster";
        :>> ownerText = "SW: host card (E-01)";
        :>> owners = ("E-01", "host.card");
        :>> dataType = "8-byte frame";
        :>> valueRange = "DBC enumerations";
        :>> integrity = "none";
        :>> validity = "none";
        :>> rate = "1 Hz, or at once on an alert change (carcontroller.py:289)";
        :>> reaction = "— (QM display); must not create a false engagement indication (DFI-15)";
        :>> tsrText = "309 (AOU-12)";
        :>> tsr = ("TSR-309");
        :>> asil = "QM";
        :>> tests = ("VS-SI-24");
    }
    item <'S-06'> s_06 : Signal {
        doc /* WHEEL_SPEED_FR/FL/RR/RL, 0xAA: per wheel k = 0…3 (FR, FL, RR, RL), bytes 2k and 2k+1, big-endian, bits 0–6 of byte 2k (high) and byte 2k+1 (low); fault flag bit 16k+7 (provisional, from the DBC, not yet confirmed independently: LAYOUT-CHECK-2026-10-13 LC-01) */
        :>> group = "Vehicle CAN signals";
        :>> hsi = ("HSI-04");
        :>> direction = "vehicle → MCU (RX, bus 0)";
        :>> ownerText = "SW: E-03a envelope RX hook (modes/toyota.h)";
        :>> owners = ("E-03a");
        :>> dataType = "4 × 15-bit unsigned";
        :>> valueRange = "0.01 km/h, offset −67.67";
        :>> integrity = "none";
        :>> validity = "none (no checksum, no counter, toyota.h:40)";
        :>> rate = "83 Hz / required ≤ 5 periods (≤ 0.2 s, TSR-401)";
        :>> reaction = "RX fault → revoke all authority (TSR-406); frozen-payload and cross-checks (TSR-404, 405(a))";
        :>> tsrText = "401, 404, 405, 406";
        :>> tsr = ("TSR-401", "TSR-404", "TSR-405", "TSR-406");
        :>> asil = "B‡";
        :>> tests = ("VS-SI-12", "VS-SI-13", "VS-FI-02", "VS-FI-04", "VS-FI-05");
    }
    item <'S-07'> s_07 : Signal {
        doc /* STEER_TORQUE_DRIVER, 0x260 */
        :>> group = "Vehicle CAN signals";
        :>> hsi = ("HSI-04");
        :>> direction = "vehicle → MCU";
        :>> ownerText = "SW: E-03a envelope RX hook (modes/toyota.h)";
        :>> owners = ("E-03a");
        :>> dataType = "int16, signed";
        :>> valueRange = "raw";
        :>> integrity = "8-bit additive CHECKSUM";
        :>> validity = "none (no counter, toyota.h:41)";
        :>> rate = "50 Hz / ≤ 0.2 s; STEER_ANGLE_INITIALIZING bit 3 is the message's quality flag, checked only in LTA mode, not in the reference (LKA) configuration (provisional, from the DBC, not yet confirmed independently: LAYOUT-CHECK-2026-10-13 LC-01)";
        :>> reaction = "Driver override → torque reduction or revoke (TSR-304); RX fault → TSR-406";
        :>> tsrText = "304, 401…406";
        :>> tsr = ("TSR-304", "TSR-401", "TSR-402", "TSR-403", "TSR-404", "TSR-405", "TSR-406");
        :>> asil = "B‡";
        :>> tests = ("VS-SI-03", "VS-SI-14", "VS-FI-02");
    }
    item <'S-08'> s_08 : Signal {
        doc /* STEER_TORQUE_EPS, 0x260 */
        :>> group = "Vehicle CAN signals";
        :>> hsi = ("HSI-04");
        :>> direction = "vehicle → MCU";
        :>> ownerText = "SW: E-03a envelope RX hook; host selfdrived (TSR-626)";
        :>> owners = ("E-03a", "host.selfdrived");
        :>> dataType = "int16, signed";
        :>> valueRange = "raw (EPS scale param 73)";
        :>> integrity = "as S-07";
        :>> validity = "as S-07";
        :>> rate = "50 Hz / ≤ 0.2 s";
        :>> reaction = "Measured-torque tracking (TSR-104); EPS not following command → SoC disable (TSR-626(b))";
        :>> tsrText = "104, 405(d), 626";
        :>> tsr = ("TSR-104", "TSR-405", "TSR-626");
        :>> asil = "B‡";
        :>> tests = ("VS-SI-15", "VS-FI-05");
    }
    item <'S-09'> s_09 : Signal {
        doc /* CRUISE_ACTIVE, 0x1D2 PCM_CRUISE bit 5 */
        :>> group = "Vehicle CAN signals";
        :>> hsi = ("HSI-04");
        :>> direction = "vehicle → MCU";
        :>> ownerText = "SW: E-03a envelope RX hook (modes/toyota.h)";
        :>> owners = ("E-03a");
        :>> dataType = "bool";
        :>> valueRange = "0 / 1";
        :>> integrity = "8-bit CHECKSUM";
        :>> validity = "none (no counter)";
        :>> rate = "33 Hz / ≤ 0.2 s";
        :>> reaction = "Rising edge grants, low revokes (TSR-301); RX fault → TSR-406";
        :>> tsrText = "301, 401…406";
        :>> tsr = ("TSR-301", "TSR-401", "TSR-402", "TSR-403", "TSR-404", "TSR-405", "TSR-406");
        :>> asil = "B‡";
        :>> tests = ("VS-SI-01", "VS-SI-02", "VS-SI-13");
    }
    item <'S-10'> s_10 : Signal {
        doc /* GAS_RELEASED, 0x1D2 bit 4 */
        :>> group = "Vehicle CAN signals";
        :>> hsi = ("HSI-04");
        :>> direction = "vehicle → MCU";
        :>> ownerText = "SW: E-03a envelope RX hook (modes/toyota.h)";
        :>> owners = ("E-03a");
        :>> dataType = "bool";
        :>> valueRange = "0 / 1";
        :>> integrity = "as S-09";
        :>> validity = "as S-09";
        :>> rate = "as S-09";
        :>> reaction = "Gas pressed → only the inactive acceleration (TSR-305)";
        :>> tsrText = "305";
        :>> tsr = ("TSR-305");
        :>> asil = "B‡";
        :>> tests = ("VS-SI-04");
    }
    item <'S-11'> s_11 : Signal {
        doc /* BRAKE_PRESSED, 0x226 BRAKE_MODULE bit 37 */
        :>> group = "Vehicle CAN signals";
        :>> hsi = ("HSI-04");
        :>> direction = "vehicle → MCU";
        :>> ownerText = "SW: E-03a envelope RX hook (modes/toyota.h)";
        :>> owners = ("E-03a");
        :>> dataType = "bool";
        :>> valueRange = "0 / 1";
        :>> integrity = "none (toyota.h:46, checksum ignored)";
        :>> validity = "none";
        :>> rate = "40 Hz / ≤ 0.2 s";
        :>> reaction = "Brake → revoke (TSR-302); disagreement with S-13 → assume pressed (TSR-405(b))";
        :>> tsrText = "302, 405";
        :>> tsr = ("TSR-302", "TSR-405");
        :>> asil = "B‡";
        :>> tests = ("VS-SI-02", "VS-SI-13", "VS-FI-05");
    }
    item <'S-12'> s_12 : Signal {
        doc /* LKA_STATE, 0x262 EPS_STATUS, byte 3 bits 1–7 (provisional, from the DBC, not yet confirmed independently: LAYOUT-CHECK-2026-10-13 LC-01) */
        :>> group = "Vehicle CAN signals";
        :>> hsi = ("HSI-04");
        :>> direction = "vehicle → MCU (reference build, opendbc 242d63d) / SoC";
        :>> ownerText = "SW: E-03a (presence, checksum, timeout; fault codes refuse LKA actuation); host card (fault codes, alert)";
        :>> owners = ("E-03a", "host.card");
        :>> dataType = "7-bit unsigned";
        :>> valueRange = "EPS state codes (carstate.py:19-22)";
        :>> integrity = "8-bit CHECKSUM";
        :>> validity = "none";
        :>> rate = "25 Hz nominal (to be measured) / ≤ 0.3 s";
        :>> reaction = "EPS fault → envelope refuses LKA torque and steer request and reports it (pandaState.epsFault) (TSR-110, implemented in the reference build); siren when the fault persists 1 s while engaged (TSR-516(b), panda b790fca)";
        :>> tsrText = "110, 607";
        :>> tsr = ("TSR-110", "TSR-607");
        :>> asil = "B (SG-02)";
        :>> tests = ("VS-SI-17");
    }
    item <'S-13'> s_13 : Signal {
        doc /* BRAKE_PRESSED, MAIN_ON, ACC_FAULTED, 0x1D3 PCM_CRUISE_2; MAIN_ON bit 15 (provisional, from the DBC, not yet confirmed independently: LAYOUT-CHECK-2026-10-13 LC-01); BRAKE_PRESSED and ACC_FAULTED positions not stated */
        :>> group = "Vehicle CAN signals";
        :>> hsi = ("HSI-04");
        :>> direction = "vehicle → MCU (reference build: RX check only, opendbc 98404a4) / SoC";
        :>> ownerText = "SW: E-03a (presence, checksum, timeout; MAIN_ON vs CRUISE_ACTIVE, opendbc 875e325; BRAKE_PRESSED cross-check open); host card";
        :>> owners = ("E-03a", "host.card");
        :>> dataType = "bool";
        :>> valueRange = "0 / 1";
        :>> integrity = "8-bit CHECKSUM";
        :>> validity = "none";
        :>> rate = "33 Hz nominal (to be measured) / ≤ 0.2 s";
        :>> reaction = "MAIN_ON = 0 with CRUISE_ACTIVE: no engagement, revoke after 150 ms (TSR-405(c), implemented); BRAKE_PRESSED vs S-11 (TSR-405(b), open: bit semantics unknown); ACC fault → SoC disable (TSR-618)";
        :>> tsrText = "405, 618";
        :>> tsr = ("TSR-405", "TSR-618");
        :>> asil = "B‡ / QM";
        :>> tests = ("VS-SI-13", "VS-FI-05");
    }
    item <'S-14'> s_14 : Signal {
        doc /* SPEED, ENCODER, 0xB4 */
        :>> group = "Vehicle CAN signals";
        :>> hsi = ("HSI-04");
        :>> direction = "vehicle → MCU (proposed)";
        :>> ownerText = "SW: E-03a envelope RX hook (modes/toyota.h)";
        :>> owners = ("E-03a");
        :>> dataType = "16-bit unsigned; 8-bit";
        :>> valueRange = "0.01 km/h; counts";
        :>> integrity = "8-bit CHECKSUM";
        :>> validity = "ENCODER changes while moving";
        :>> rate = "TBD / ≤ 0.2 s";
        :>> reaction = "Cross-check with S-06 (TSR-405(a)); frozen ENCODER (TSR-404)";
        :>> tsrText = "404, 405";
        :>> tsr = ("TSR-404", "TSR-405");
        :>> asil = "B‡";
        :>> tests = ("VS-FI-02", "VS-FI-05");
    }
    item <'S-15'> s_15 : Signal {
        doc /* Camera-side frames incl. PRE_COLLISION 0x283, PRE_COLLISION_2 0x344, PCS_HUD 0x411 */
        :>> group = "Vehicle CAN signals";
        :>> hsi = ("HSI-04");
        :>> direction = "camera → MCU → vehicle (forwarded bus 2 → bus 0)";
        :>> ownerText = "SW: E-03b forwarding (drivers/fdcan.h); HW: FDCAN, transceivers";
        :>> owners = ("E-03b");
        :>> dataType = "CAN frames";
        :>> valueRange = "unchanged";
        :>> integrity = "CAN CRC; OEM checksums where defined";
        :>> validity = "camera-side reception supervised (TSR-711)";
        :>> rate = "OEM rate (to be measured, WP-S-04 OI-4) / forwarding latency ≤ 1 ms; loss detected ≤ 0.1 s";
        :>> reaction = "Forwarding stopped → relay released (TSR-711, TSR-706); SoC frames with these IDs refused (TSR-705)";
        :>> tsrText = "704, 705, 707, 711";
        :>> tsr = ("TSR-704", "TSR-705", "TSR-707", "TSR-711");
        :>> asil = "B";
        :>> tests = ("VS-SI-20", "VS-SI-21", "VS-FI-24");
    }
    item <'S-16'> s_16 : Signal {
        doc /* SPI transfer (header, payload) */
        :>> group = "SoC ↔ safety MCU signals";
        :>> hsi = ("HSI-01", "HSI-02", "HSI-03");
        :>> direction = "SoC ↔ MCU";
        :>> ownerText = "SW: E-03b drivers/spi.h; host pandad; HW: SPI4, DMA2";
        :>> owners = ("E-03b", "host.pandad");
        :>> dataType = "7-byte header + payload ≤ 4096 B";
        :>> valueRange = "lengths bounded by the buffer";
        :>> integrity = "8-bit XOR, seed 0xAB (§4.1); required CRC (TSR-410)";
        :>> validity = "none; required sequence counter (TSR-411)";
        :>> rate = "≈ 100 Hz (pandad loop) / required ≤ 2 control periods for commands (TSR-411, TSR-614)";
        :>> reaction = "NACK; required: stale or corrupt command → SS-L / SS-G (TSR-410…413)";
        :>> tsrText = "410…413";
        :>> tsr = ("TSR-410", "TSR-411", "TSR-412", "TSR-413");
        :>> asil = "B‡";
        :>> tests = ("VS-SI-09", "VS-SI-10", "VS-FI-06", "VS-FI-07", "VS-FI-08");
    }
    item <'S-17'> s_17 : Signal {
        doc /* CAN TX packet from SoC (endpoint 3) */
        :>> group = "SoC ↔ safety MCU signals";
        :>> hsi = ("HSI-01", "HSI-02", "HSI-03");
        :>> direction = "SoC → MCU";
        :>> ownerText = "SW: E-03b can_comms.h; host pandad";
        :>> owners = ("E-03b", "host.pandad");
        :>> dataType = "6-byte header + ≤ 8 B payload";
        :>> valueRange = "DLC, bus, address";
        :>> integrity = "8-bit XOR per packet, checked at FDCAN load (§4.3)";
        :>> validity = "none";
        :>> rate = "per control frame";
        :>> reaction = "Rejected by the TX hook → returned with rejected = 1; violation → revoke (TSR-108)";
        :>> tsrText = "108, 410, 517, 518";
        :>> tsr = ("TSR-108", "TSR-410", "TSR-517", "TSR-518");
        :>> asil = "B‡";
        :>> tests = ("VS-SI-11", "VS-SI-15", "VS-FI-14");
    }
    item <'S-18'> s_18 : Signal {
        doc /* Heartbeat 0xf3, param1 = engaged */
        :>> group = "SoC ↔ safety MCU signals";
        :>> hsi = ("HSI-01", "HSI-02", "HSI-03");
        :>> direction = "SoC → MCU";
        :>> ownerText = "SW: E-03b main_comms.h; host pandad";
        :>> owners = ("E-03b", "host.pandad");
        :>> dataType = "control request, uint16 param";
        :>> valueRange = "0 / 1";
        :>> integrity = "as S-16";
        :>> validity = "heartbeat counter";
        :>> rate = "10 Hz, sent with each pandaStates cycle (openpilot/selfdrive/pandad/pandad.cc:278), checked in the 1 Hz MCU tick / required ≤ 0.3 s loss detection (TSR-407)";
        :>> reaction = "Loss → SS-S and siren (TSR-407, TSR-516(a)); \"not engaged\" → revoke (TSR-307(a))";
        :>> tsrText = "307, 407, 409";
        :>> tsr = ("TSR-307", "TSR-407", "TSR-409");
        :>> asil = "B‡";
        :>> tests = ("VS-SI-05", "VS-SI-06", "VS-FI-10");
    }
    item <'S-19'> s_19 : Signal {
        doc /* Safety mode and param 0xdc */
        :>> group = "SoC ↔ safety MCU signals";
        :>> hsi = ("HSI-01", "HSI-02", "HSI-03");
        :>> direction = "SoC → MCU";
        :>> ownerText = "SW: E-03b main_comms.h; host pandad";
        :>> owners = ("E-03b", "host.pandad");
        :>> dataType = "control request, 2 × uint16";
        :>> valueRange = "TOYOTA mode; param 73 (EPS scale)";
        :>> integrity = "as S-16";
        :>> validity = "— (configuration)";
        :>> rate = "at start-up";
        :>> reaction = "Required: any other value in a car mode refused (TSR-512)";
        :>> tsrText = "512, 619";
        :>> tsr = ("TSR-512", "TSR-619");
        :>> asil = "B‡";
        :>> tests = ("VS-SI-07", "VS-FI-11");
    }
    item <'S-20'> s_20 : Signal {
        doc /* Configuration and debug requests (0xc5, 0xd1, 0xd8, 0xdb, 0xde, 0xe5…0xe8, 0xf1, 0xf9, 0xfc) */
        :>> group = "SoC ↔ safety MCU signals";
        :>> hsi = ("HSI-01", "HSI-02", "HSI-03");
        :>> direction = "SoC → MCU";
        :>> ownerText = "SW: E-03b main_comms.h; host pandad";
        :>> owners = ("E-03b", "host.pandad");
        :>> dataType = "control requests";
        :>> valueRange = "§4.2";
        :>> integrity = "as S-16";
        :>> validity = "—";
        :>> rate = "on request";
        :>> reaction = "Required: refused in a car safety mode (TSR-513)";
        :>> tsrText = "511, 513";
        :>> tsr = ("TSR-511", "TSR-513");
        :>> asil = "B‡";
        :>> tests = ("VS-SI-08", "VS-HW-05", "VS-FI-11");
    }
    item <'S-21'> s_21 : Signal {
        doc /* Health packet 0xd2 (health_t: controls allowed, faults, safety mode and param, TX blocked and RX invalid counts, harness status, voltage, temperature; LionDriver flags: watchdog reset, EPS fault, reference build) */
        :>> group = "SoC ↔ safety MCU signals";
        :>> hsi = ("HSI-01", "HSI-02", "HSI-03");
        :>> direction = "MCU → SoC";
        :>> ownerText = "SW: E-03b main_comms.h; host pandad, selfdrived";
        :>> owners = ("E-03b", "host.pandad", "host.selfdrived");
        :>> dataType = "packed struct (panda/board/health.h)";
        :>> valueRange = "per field";
        :>> integrity = "as S-16";
        :>> validity = "pandaStates alive check";
        :>> rate = "10 Hz pandaStates / required ≤ 0.2 s (TSR-626(a))";
        :>> reaction = "SoC immediate disable on fault flags or mismatch (TSR-615, 621, 626); in a reference build pandad sets no car safety mode without the reference-build flag (TSR-514)";
        :>> tsrText = "615, 621, 626";
        :>> tsr = ("TSR-615", "TSR-621", "TSR-626");
        :>> asil = "QM (B-sup)";
        :>> tests = ("VS-SI-06", "VS-SI-17", "VS-SI-23");
    }
    item <'S-22'> s_22 : Signal {
        doc /* Relay drive (tres PA8 / cuatro PA9; PA3) */
        :>> group = "Safety MCU hardware signals";
        :>> hsi = ("HSI-05", "HSI-06", "HSI-07", "HSI-08", "HSI-09", "HSI-10", "HSI-11", "HSI-12", "HSI-13", "HSI-14");
        :>> direction = "MCU → harness relay";
        :>> ownerText = "HW: relay driver and coil (E-05); SW: E-03b drivers/harness.h";
        :>> owners = ("E-05", "E-03b");
        :>> dataType = "GPIO, open-drain";
        :>> valueRange = "low = energised (intercept); high or reset = released";
        :>> integrity = "none";
        :>> validity = "none at the baseline; required contact readback (TSR-506)";
        :>> rate = "static / readback mismatch ≤ 0.3 s";
        :>> reaction = "Released on SS-S, MCU fault, reset, power loss (TSR-706); forwarding loss (TSR-711)";
        :>> tsrText = "506, 706, 710, 711";
        :>> tsr = ("TSR-506", "TSR-706", "TSR-710", "TSR-711");
        :>> asil = "B";
        :>> tests = ("VS-HW-01", "VS-HW-02", "VS-HW-03", "VS-HW-04", "VS-SI-18", "VS-SI-19", "VS-FI-21");
    }
    item <'S-23'> s_23 : Signal {
        doc /* SBU1 / SBU2 sense (PC4 / ADC1 ch4, PA1 / ADC1 ch17) */
        :>> group = "Safety MCU hardware signals";
        :>> hsi = ("HSI-05", "HSI-06", "HSI-07", "HSI-08", "HSI-09", "HSI-10", "HSI-11", "HSI-12", "HSI-13", "HSI-14");
        :>> direction = "harness → MCU";
        :>> ownerText = "HW: SBU divider, ADC1; SW: E-03b drivers/harness.h";
        :>> owners = ("E-03b");
        :>> dataType = "ADC, mV (reported in health_t)";
        :>> valueRange = "orientation: below avdd/2";
        :>> integrity = "none";
        :>> validity = "evaluated only while the relay is not driven";
        :>> rate = "8 Hz";
        :>> reaction = "Orientation change → CAN re-init and mode re-apply (§6); not connected → no relay drive (TSR-701)";
        :>> tsrText = "701";
        :>> tsr = ("TSR-701");
        :>> asil = "B";
        :>> tests = ("VS-HW-13", "VS-FI-28");
    }
    item <'S-24'> s_24 : Signal {
        doc /* Ignition line */
        :>> group = "Safety MCU hardware signals";
        :>> hsi = ("HSI-05", "HSI-06", "HSI-07", "HSI-08", "HSI-09", "HSI-10", "HSI-11", "HSI-12", "HSI-13", "HSI-14");
        :>> direction = "harness → MCU";
        :>> ownerText = "HW: ignition input; SW: E-03b drivers/harness.h";
        :>> owners = ("E-03b");
        :>> dataType = "digital";
        :>> valueRange = "on / off";
        :>> integrity = "none";
        :>> validity = "—";
        :>> rate = "1 Hz (panda/board/main.c:156)";
        :>> reaction = "Heartbeat loss → SS-S within ≤ 2 s regardless of ignition (TSR-510)";
        :>> tsrText = "510";
        :>> tsr = ("TSR-510");
        :>> asil = "B";
        :>> tests = ("VS-HW-14");
    }
    item <'S-25'> s_25 : Signal {
        doc /* STM_RST_N, STM_BOOT0 */
        :>> group = "Safety MCU hardware signals";
        :>> hsi = ("HSI-05", "HSI-06", "HSI-07", "HSI-08", "HSI-09", "HSI-10", "HSI-11", "HSI-12", "HSI-13", "HSI-14");
        :>> direction = "SoC → MCU";
        :>> ownerText = "HW: SoC GPIO to NRST/BOOT0; SW: host pandad through common/hardware/comma/hardware.py";
        :>> owners = ("host.pandad");
        :>> dataType = "GPIO";
        :>> valueRange = "reset / ROM bootloader";
        :>> integrity = "none";
        :>> validity = "—";
        :>> rate = "on event";
        :>> reaction = "MCU reset → relay released (TSR-502, HWSR-502c); boot protection (TSR-511)";
        :>> tsrText = "502, 511";
        :>> tsr = ("TSR-502", "TSR-511");
        :>> asil = "B‡ (+CS)";
        :>> tests = ("VS-HW-19", "VS-FI-16");
    }
    item <'S-26'> s_26 : Signal {
        doc /* Independent watchdog IWDG1 */
        :>> group = "Safety MCU hardware signals";
        :>> hsi = ("HSI-05", "HSI-06", "HSI-07", "HSI-08", "HSI-09", "HSI-10", "HSI-11", "HSI-12", "HSI-13", "HSI-14");
        :>> direction = "MCU internal";
        :>> ownerText = "HW: IWDG1 (E-04a); SW: E-03b bootstub and tick";
        :>> owners = ("E-04a", "E-03b");
        :>> dataType = "timer";
        :>> valueRange = "timeout ≤ 0.1 s (§7)";
        :>> integrity = "—";
        :>> validity = "serviced after the safety task completes";
        :>> rate = "—";
        :>> reaction = "Reset → SS-S (TSR-501, 502)";
        :>> tsrText = "501, 502";
        :>> tsr = ("TSR-501", "TSR-502");
        :>> asil = "B‡";
        :>> tests = ("VS-HW-06", "VS-HW-07", "VS-FI-17");
    }
    item <'S-27'> s_27 : Signal {
        doc /* Siren output (DAC/DMA and codec over I2C5, or SAI4 amplifier) */
        :>> group = "Safety MCU hardware signals";
        :>> hsi = ("HSI-05", "HSI-06", "HSI-07", "HSI-08", "HSI-09", "HSI-10", "HSI-11", "HSI-12", "HSI-13", "HSI-14");
        :>> direction = "MCU → speaker";
        :>> ownerText = "HW: codec or amplifier, speaker; SW: E-03b drivers/fake_siren.h";
        :>> owners = ("E-03b");
        :>> dataType = "audio";
        :>> valueRange = "4 Hz pattern";
        :>> integrity = "none";
        :>> validity = "required start-up test (TSR-515)";
        :>> rate = "≤ 0.5 s after trigger";
        :>> reaction = "Triggers per TSR-516(a)…(c)";
        :>> tsrText = "515, 516";
        :>> tsr = ("TSR-515", "TSR-516");
        :>> asil = "B";
        :>> tests = ("VS-HW-21");
    }
    item <'S-28'> s_28 : Signal {
        doc /* Supply voltage (ADC1 input divider) */
        :>> group = "Safety MCU hardware signals";
        :>> hsi = ("HSI-05", "HSI-06", "HSI-07", "HSI-08", "HSI-09", "HSI-10", "HSI-11", "HSI-12", "HSI-13", "HSI-14");
        :>> direction = "supply → MCU";
        :>> ownerText = "HW: input divider, ADC1, BOR/PVD; SW: E-03b";
        :>> owners = ("E-03b");
        :>> dataType = "ADC, mV (health_t.voltage_pkt)";
        :>> valueRange = "operating range per HWSR-505";
        :>> integrity = "none";
        :>> validity = "—";
        :>> rate = "on each health request (10 Hz)";
        :>> reaction = "Required: out of range → SS-S (TSR-505); BOR / PVD";
        :>> tsrText = "505";
        :>> tsr = ("TSR-505");
        :>> asil = "B‡";
        :>> tests = ("VS-HW-09", "VS-HW-10", "VS-FI-15");
    }
    item <'S-29'> s_29 : Signal {
        doc /* Die temperature (DTS) */
        :>> group = "Safety MCU hardware signals";
        :>> hsi = ("HSI-05", "HSI-06", "HSI-07", "HSI-08", "HSI-09", "HSI-10", "HSI-11", "HSI-12", "HSI-13", "HSI-14");
        :>> direction = "MCU internal";
        :>> ownerText = "HW: DTS (E-04a); SW: E-03b";
        :>> owners = ("E-04a", "E-03b");
        :>> dataType = "°C (health_t.temperature_pkt)";
        :>> valueRange = "specified MCU range";
        :>> integrity = "none";
        :>> validity = "—";
        :>> rate = "on each health request (10 Hz)";
        :>> reaction = "Required: out of range → SS-S (TSR-509)";
        :>> tsrText = "509";
        :>> tsr = ("TSR-509");
        :>> asil = "B";
        :>> tests = ("VS-HW-15", "VS-FI-26");
    }

    item def HsiResponsibility {
        doc /* What the hardware and the software each provide and must do at one interface HSI-nn, who detects
               a failure of the other side and how the item reacts (WP-S-05 §11.4). */
        attribute hardware : String;
        attribute software : String;
        attribute detection : String;
        attribute reaction : String;
        attribute shared : String;
        attribute hwOwnerText : String;
        attribute swOwnerText : String;
        attribute hwOwners : String[0..*];
        attribute swOwners : String[0..*];
        attribute tsr : String[0..*];
        attribute status : String;
        attribute hwResource : String;
        attribute hwParts : String[0..*];
    }

    item <'HSI-01'> hsi_01 : HsiResponsibility {
        doc /* SoC ↔ MCU SPI link */
        :>> hardware = "SPI4 slave and DMA2 streams into the SRAM1/2 buffers (§3, §8)";
        :>> software = "Check every transfer and bound every length against the MCU buffer (TSR-410, 412); keep the DMA buffers apart from the safety state (TSR-507, HSI-14)";
        :>> detection = "SW: per-transfer checksum and length check";
        :>> reaction = "Transfer refused (NACK) and counted; an error burst while engaged revokes authority (TSR-413)";
        :>> shared = "—";
        :>> hwOwnerText = "E-04a; E-04b";
        :>> swOwnerText = "E-03b; host pandad";
        :>> hwOwners = ("E-04a", "E-04b");
        :>> swOwners = ("E-03b", "host.pandad");
        :>> tsr = ("TSR-410", "TSR-412", "TSR-507", "TSR-413");
        :>> status = "partial";
        :>> hwResource = "SPI4, DMA2 streams 2/3, SRAM1/2 buffers";
        :>> hwParts = ("spi4", "memories");
    }
    item <'HSI-02'> hsi_02 : HsiResponsibility {
        doc /* Control requests over SPI endpoint 0 */
        :>> hardware = "Nothing beyond HSI-01: requests arrive on SPI endpoint 0";
        :>> software = "Accept only the requests the mode allows (TSR-512, 513) and supervise the heartbeat (TSR-407, 409)";
        :>> detection = "SW: heartbeat monitor, reference lock";
        :>> reaction = "Authority revoked with the siren (TSR-516); a refused request leaves the state unchanged";
        :>> shared = "HSI-01";
        :>> hwOwnerText = "E-04a";
        :>> swOwnerText = "E-03b; host pandad";
        :>> hwOwners = ("E-04a");
        :>> swOwners = ("E-03b", "host.pandad");
        :>> tsr = ("TSR-512", "TSR-513", "TSR-407", "TSR-409", "TSR-516");
        :>> status = "partial";
        :>> hwResource = "—";
        :>> hwParts = "";
    }
    item <'HSI-03'> hsi_03 : HsiResponsibility {
        doc /* CAN packet stream over SPI endpoints 1/3 */
        :>> hardware = "Nothing beyond HSI-01: CAN packets on SPI endpoints 1 and 3";
        :>> software = "Unpack the stream and pass every actuation frame through the TX hook (TSR-410, 411, 518)";
        :>> detection = "SW: per-packet checksum, TX hook, TX-rate check";
        :>> reaction = "Frame rejected and returned to the SoC; a rate excess revokes authority (TSR-518)";
        :>> shared = "HSI-01";
        :>> hwOwnerText = "E-04a";
        :>> swOwnerText = "E-03a; E-03b; host pandad";
        :>> hwOwners = ("E-04a");
        :>> swOwners = ("E-03a", "E-03b", "host.pandad");
        :>> tsr = ("TSR-410", "TSR-411", "TSR-518");
        :>> status = "partial";
        :>> hwResource = "SPI4";
        :>> hwParts = ("spi4");
    }
    item <'HSI-04'> hsi_04 : HsiResponsibility {
        doc /* FDCAN1–3 and transceivers */
        :>> hardware = "FDCAN1–3 controllers with the CAN CRC, error counters and bus-off, and the transceiver enable lines (§5)";
        :>> software = "Check every RX message the envelope uses (TSR-401…406), forward camera frames unchanged (TSR-704, 707), send only through the TX hook and react to bus-off (TSR-508)";
        :>> detection = "HW: CAN CRC and error confinement; SW: RX checks and timeouts";
        :>> reaction = "An RX fault revokes authority; bus-off is counted and the core reset, a safety reaction is required (HWSR-508)";
        :>> shared = "One TX queue for forwarded and host frames (SDF-05)";
        :>> hwOwnerText = "E-04a";
        :>> swOwnerText = "E-03a; E-03b";
        :>> hwOwners = ("E-04a");
        :>> swOwners = ("E-03a", "E-03b");
        :>> tsr = ("TSR-401", "TSR-402", "TSR-403", "TSR-404", "TSR-405", "TSR-406", "TSR-704", "TSR-707", "TSR-508");
        :>> status = "partial";
        :>> hwResource = "FDCAN, transceiver enable GPIOs";
        :>> hwParts = ("fdcanPeripherals", "gpio");
    }
    item <'HSI-05'> hsi_05 : HsiResponsibility {
        doc /* Harness relay drive */
        :>> hardware = "Open-drain GPIO driving the intercept relay in the harness; released at reset (to be confirmed, AOU-13)";
        :>> software = "Drive the relay only in a car mode with a harness detected, and release it in SILENT, NOOUTPUT and ELM327 and in the safe state (TSR-506, 706)";
        :>> detection = "Not detected: no readback (GAP-12); required by HWSR-506a";
        :>> reaction = "Relay released: the stock camera path is restored (SG-07)";
        :>> shared = "—";
        :>> hwOwnerText = "E-04a; E-05";
        :>> swOwnerText = "E-03b";
        :>> hwOwners = ("E-04a", "E-05");
        :>> swOwners = ("E-03b");
        :>> tsr = ("TSR-506", "TSR-706");
        :>> status = "partial";
        :>> hwResource = "GPIO (open-drain, active-low)";
        :>> hwParts = ("gpio");
    }
    item <'HSI-06'> hsi_06 : HsiResponsibility {
        doc /* Harness orientation sense */
        :>> hardware = "ADC1 channels 4 and 17 on the SBU lines (§6)";
        :>> software = "Detect the orientation while the relay is not driven, map CAN and relay pins to it, and re-initialise on a change (TSR-701)";
        :>> detection = "SW: ADC threshold at 8 Hz";
        :>> reaction = "CAN re-initialised and the safety mode re-applied";
        :>> shared = "ADC1 with HSI-13";
        :>> hwOwnerText = "E-04a; E-05";
        :>> swOwnerText = "E-03b";
        :>> hwOwners = ("E-04a", "E-05");
        :>> swOwners = ("E-03b");
        :>> tsr = ("TSR-701");
        :>> status = "partial";
        :>> hwResource = "ADC1 ch4/ch17 on SBU1/SBU2";
        :>> hwParts = ("adc");
    }
    item <'HSI-07'> hsi_07 : HsiResponsibility {
        doc /* Ignition line */
        :>> hardware = "Digital input on the SBU ignition line";
        :>> software = "Use the line to select the heartbeat timeouts and the power state (TSR-510)";
        :>> detection = "Not detected: no plausibility check of the line (LS-28)";
        :>> reaction = "—";
        :>> shared = "—";
        :>> hwOwnerText = "E-04a; E-05";
        :>> swOwnerText = "E-03b";
        :>> hwOwners = ("E-04a", "E-05");
        :>> swOwners = ("E-03b");
        :>> tsr = ("TSR-510");
        :>> status = "partial";
        :>> hwResource = "SBU GPIO input";
        :>> hwParts = ("gpio");
    }
    item <'HSI-08'> hsi_08 : HsiResponsibility {
        doc /* Reset / boot pins from SoC */
        :>> hardware = "SoC GPIOs to NRST and BOOT0; ST ROM bootloader on BOOT0 high (§7)";
        :>> software = "Keep the MCU outputs safe during reset and boot (TSR-502, HWSR-502c) and keep flash closed to the ROM bootloader (TSR-511)";
        :>> detection = "SW: reset cause reported in the health packet";
        :>> reaction = "Restart in SILENT with the relay released; RDP and WRP are required (TSR-511)";
        :>> shared = "—";
        :>> hwOwnerText = "E-04a; E-04b";
        :>> swOwnerText = "E-03b; host pandad";
        :>> hwOwners = ("E-04a", "E-04b");
        :>> swOwners = ("E-03b", "host.pandad");
        :>> tsr = ("TSR-502", "TSR-511");
        :>> status = "partial";
        :>> hwResource = "SoC GPIO → MCU NRST, BOOT0";
        :>> hwParts = ("gpio");
    }
    item <'HSI-09'> hsi_09 : HsiResponsibility {
        doc /* Watchdog */
        :>> hardware = "IWDG1 window watchdog, 90 ms nominal, on its own clock";
        :>> software = "Start it at the first relay drive and service it only after the 100 Hz safety task completes (TSR-501)";
        :>> detection = "HW: watchdog timeout";
        :>> reaction = "MCU reset: relay released, restart in SILENT";
        :>> shared = "—";
        :>> hwOwnerText = "E-04a";
        :>> swOwnerText = "E-03b";
        :>> hwOwners = ("E-04a");
        :>> swOwners = ("E-03b");
        :>> tsr = ("TSR-501");
        :>> status = "in place";
        :>> hwResource = "IWDG1 (window mode, 90 ms nominal, started at the first relay energisation; panda 3859fa8), software timestamp check";
        :>> hwParts = ("iwdg1");
    }
    item <'HSI-10'> hsi_10 : HsiResponsibility {
        doc /* Fault / health monitors */
        :>> hardware = "Fault vectors (NMI, HardFault), clock security system, die temperature sensor, interrupt-rate counters";
        :>> software = "Classify each fault and take the safe state (TSR-502…505, 509); today most are reported only";
        :>> detection = "HW: CSS and fault vectors; SW: counters and register checks";
        :>> reaction = "NMI and HardFault reset the MCU; the other faults are reported only, a reaction is required";
        :>> shared = "—";
        :>> hwOwnerText = "E-04a";
        :>> swOwnerText = "E-03b";
        :>> hwOwners = ("E-04a");
        :>> swOwners = ("E-03b");
        :>> tsr = ("TSR-502", "TSR-503", "TSR-504", "TSR-505", "TSR-509");
        :>> status = "partial";
        :>> hwResource = "NVIC, RCC CSS, DTS, ADC, interrupt-rate counters";
        :>> hwParts = ("core", "clock", "adc");
    }
    item <'HSI-11'> hsi_11 : HsiResponsibility {
        doc /* Siren */
        :>> hardware = "DAC with DMA and an audio codec over I2C5, or an amplifier, to the speaker";
        :>> software = "Sound the siren when authority is revoked or the EPS fault persists (TSR-516), and test it at start-up (TSR-515)";
        :>> detection = "Not detected: no feedback from the speaker; a start-up test is required";
        :>> reaction = "—";
        :>> shared = "The speaker with the SoC's audio (DFA)";
        :>> hwOwnerText = "E-04a; E-04b";
        :>> swOwnerText = "E-03b";
        :>> hwOwners = ("E-04a", "E-04b");
        :>> swOwners = ("E-03b");
        :>> tsr = ("TSR-516", "TSR-515");
        :>> status = "partial";
        :>> hwResource = "DAC/DMA + codec over I2C5 (board-dependent)";
        :>> hwParts = ("sirenPath");
    }
    item <'HSI-12'> hsi_12 : HsiResponsibility {
        doc /* Flash and bootstub */
        :>> hardware = "Flash bank 1: bootstub in sector 0, application from 0x08020000; RDP and WRP option bytes";
        :>> software = "Verify the application's signature before it runs (TSR-511, 514) and its CRC at start-up and periodically (TSR-503)";
        :>> detection = "SW: signature check at boot";
        :>> reaction = "The bootstub does not start the application and enters the soft flasher";
        :>> shared = "—";
        :>> hwOwnerText = "E-04a";
        :>> swOwnerText = "E-03b";
        :>> hwOwners = ("E-04a");
        :>> swOwners = ("E-03b");
        :>> tsr = ("TSR-511", "TSR-514", "TSR-503");
        :>> status = "partial";
        :>> hwResource = "Flash bank 1, sector 0 bootstub, app at 0x08020000";
        :>> hwParts = ("memories");
    }
    item <'HSI-13'> hsi_13 : HsiResponsibility {
        doc /* Supply measurement */
        :>> hardware = "ADC1 with an input divider on the supply; BOR and PVD in the MCU";
        :>> software = "Measure the supply and take the safe state outside the operating range (TSR-505, HWSR-505b)";
        :>> detection = "SW: ADC reading on each health request; BOR and PVD are not configured yet";
        :>> reaction = "Required: safe state outside the range";
        :>> shared = "ADC1 with HSI-06";
        :>> hwOwnerText = "E-04a";
        :>> swOwnerText = "E-03b";
        :>> hwOwners = ("E-04a");
        :>> swOwners = ("E-03b");
        :>> tsr = ("TSR-505");
        :>> status = "partial";
        :>> hwResource = "ADC1 (input divider)";
        :>> hwParts = ("adc", "supply");
    }
    item <'HSI-14'> hsi_14 : HsiResponsibility {
        doc /* MPU, RAM ECC (to be added) */
        :>> hardware = "Cortex-M7 MPU and RAM ECC (RAMECC)";
        :>> software = "Configure MPU regions so DMA and non-safety code cannot reach the safety state, and handle ECC errors (TSR-503, 507)";
        :>> detection = "HW: MPU fault and ECC error, once configured";
        :>> reaction = "Required: safe state";
        :>> shared = "—";
        :>> hwOwnerText = "E-04a";
        :>> swOwnerText = "E-03b";
        :>> hwOwners = ("E-04a");
        :>> swOwners = ("E-03b");
        :>> tsr = ("TSR-503", "TSR-507");
        :>> status = "missing";
        :>> hwResource = "Cortex-M7 MPU, RAMECC";
        :>> hwParts = ("core", "memories");
    }
}
