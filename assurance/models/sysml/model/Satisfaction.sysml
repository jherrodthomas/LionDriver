// GENERATED by assurance/models/sysml/tools/gen_requirements.py from the work products. Do not edit;
// change the work product and regenerate (README §7).

package LionDriverSatisfaction {
    doc /* Each requirement satisfied by the elements its allocation names. Allocations to EXT, OPS, ENV and USR,
           and text that names no element, give no satisfy relationship; check R2 reports them. */

    private import LionDriverRequirements::*;
    private import LionDriverArchitecture::*;

    satisfy sg_01 by context.ldsda;
    satisfy sg_02 by context.ldsda;
    satisfy sg_03 by context.ldsda;
    satisfy sg_04 by context.ldsda;
    satisfy sg_05 by context.ldsda;
    satisfy sg_06 by context.ldsda;
    satisfy sg_07 by context.ldsda;
    satisfy sg_08 by context.ldsda;
    satisfy fsr_01_01 by context.ldsda.safetyFirmware;
    satisfy fsr_01_02 by context.ldsda.safetyFirmware;
    satisfy fsr_01_03 by context.ldsda.safetyFirmware;
    satisfy fsr_01_04 by context.ldsda.safetyFirmware;
    satisfy fsr_01_05 by context.ldsda.safetyFirmware;
    satisfy fsr_01_06 by context.ldsda.safetyFirmware;
    satisfy fsr_01_07 by context.ldsda.safetyFirmware;
    satisfy fsr_01_08 by context.ldsda.safetyFirmware;
    satisfy fsr_01_09 by context.ldsda.safetyFirmware;
    satisfy fsr_01_10 by context.ldsda.safetyFirmware;
    satisfy fsr_01_11 by context.ldsda.safetyFirmware;
    satisfy fsr_01_11 by context.ldsda.harness;
    satisfy fsr_01_12 by context.ldsda.safetyFirmware;
    satisfy fsr_01_14 by context.ldsda.socSoftware;
    satisfy fsr_02_01 by context.ldsda.safetyFirmware;
    satisfy fsr_02_01 by context.ldsda.socSoftware;
    satisfy fsr_02_02 by context.ldsda.socSoftware;
    satisfy fsr_02_02 by context.ldsda.safetyFirmware;
    satisfy fsr_02_03 by context.ldsda.socSoftware;
    satisfy fsr_02_03 by context.ldsda.safetyFirmware;
    satisfy fsr_02_04 by context.ldsda.socSoftware;
    satisfy fsr_02_04 by context.ldsda.safetyFirmware;
    satisfy fsr_02_05 by context.ldsda.safetyFirmware;
    satisfy fsr_02_06 by context.ldsda.socSoftware;
    satisfy fsr_02_06 by context.ldsda.mlModels;
    satisfy fsr_02_07 by context.ldsda.socSoftware;
    satisfy fsr_02_08 by context.ldsda.socSoftware;
    satisfy fsr_02_09 by context.ldsda.socSoftware;
    satisfy fsr_02_10 by context.ldsda.socSoftware;
    satisfy fsr_02_10 by context.ldsda.safetyFirmware;
    satisfy fsr_02_11 by context.ldsda.socSoftware;
    satisfy fsr_02_11 by context.ldsda.safetyFirmware;
    satisfy fsr_02_12 by context.ldsda.socSoftware;
    satisfy fsr_03_01 by context.ldsda.safetyFirmware;
    satisfy fsr_03_02 by context.ldsda.safetyFirmware;
    satisfy fsr_03_03 by context.ldsda.safetyFirmware;
    satisfy fsr_03_04 by context.ldsda.safetyFirmware;
    satisfy fsr_03_05 by context.ldsda.safetyFirmware;
    satisfy fsr_03_05 by context.ldsda.socSoftware;
    satisfy fsr_04_01 by context.ldsda.safetyFirmware;
    satisfy fsr_04_02 by context.ldsda.safetyFirmware;
    satisfy fsr_04_03 by context.ldsda.socSoftware;
    satisfy fsr_04_03 by context.ldsda.safetyFirmware;
    satisfy fsr_04_04 by context.ldsda.safetyFirmware;
    satisfy fsr_04_05 by context.ldsda.socSoftware;
    satisfy fsr_04_05 by context.ldsda.safetyFirmware;
    satisfy fsr_04_06 by context.ldsda.socSoftware;
    satisfy fsr_05_01 by context.ldsda.safetyFirmware;
    satisfy fsr_05_02 by context.ldsda.safetyFirmware;
    satisfy fsr_05_03 by context.ldsda.safetyFirmware;
    satisfy fsr_05_03 by context.ldsda.socSoftware;
    satisfy fsr_05_04 by context.ldsda.safetyFirmware;
    satisfy fsr_05_05 by context.ldsda.safetyFirmware;
    satisfy fsr_05_06 by context.ldsda.socSoftware;
    satisfy fsr_05_06 by context.ldsda.safetyFirmware;
    satisfy fsr_06_01 by context.ldsda.socSoftware;
    satisfy fsr_06_01 by context.ldsda.safetyFirmware;
    satisfy fsr_06_02 by context.ldsda.socSoftware;
    satisfy fsr_06_02 by context.ldsda.safetyFirmware;
    satisfy fsr_06_03 by context.ldsda.socSoftware;
    satisfy fsr_06_04 by context.ldsda.socSoftware;
    satisfy fsr_06_04 by context.ldsda.safetyFirmware;
    satisfy fsr_07_01 by context.ldsda.safetyFirmware;
    satisfy fsr_07_02 by context.ldsda.safetyFirmware;
    satisfy fsr_07_03 by context.ldsda.harness;
    satisfy fsr_07_03 by context.ldsda.safetyFirmware;
    satisfy fsr_07_05 by context.ldsda.socSoftware;
    satisfy fsr_07_06 by context.ldsda.safetyFirmware;
    satisfy fsr_07_06 by context.ldsda.harness;
    satisfy fsr_07_06 by context.ldsda.socSoftware;
    satisfy fsr_07_07 by context.ldsda.socSoftware;
    satisfy fsr_08_01 by context.ldsda.socSoftware;
    satisfy tsr_101 by context.ldsda.safetyFirmware;
    satisfy tsr_102 by context.ldsda.safetyFirmware;
    satisfy tsr_103 by context.ldsda.safetyFirmware;
    satisfy tsr_104 by context.ldsda.safetyFirmware;
    satisfy tsr_105 by context.ldsda.safetyFirmware;
    satisfy tsr_106 by context.ldsda.safetyFirmware;
    satisfy tsr_107 by context.ldsda.safetyFirmware;
    satisfy tsr_108 by context.ldsda.safetyFirmware;
    satisfy tsr_109 by context.ldsda.safetyFirmware;
    satisfy tsr_110 by context.ldsda.safetyFirmware;
    satisfy tsr_110 by context.ldsda.socSoftware;
    satisfy tsr_201 by context.ldsda.safetyFirmware;
    satisfy tsr_202 by context.ldsda.safetyFirmware;
    satisfy tsr_203 by context.ldsda.safetyFirmware;
    satisfy tsr_204 by context.ldsda.safetyFirmware;
    satisfy tsr_205 by context.ldsda.safetyFirmware;
    satisfy tsr_206 by context.ldsda.safetyFirmware;
    satisfy tsr_207 by context.ldsda.safetyFirmware;
    satisfy tsr_301 by context.ldsda.safetyFirmware;
    satisfy tsr_302 by context.ldsda.safetyFirmware;
    satisfy tsr_303 by context.ldsda.socSoftware;
    satisfy tsr_304 by context.ldsda.safetyFirmware;
    satisfy tsr_305 by context.ldsda.safetyFirmware;
    satisfy tsr_306 by context.ldsda.safetyFirmware;
    satisfy tsr_307 by context.ldsda.safetyFirmware;
    satisfy tsr_307 by context.ldsda.socSoftware;
    satisfy tsr_308 by context.ldsda.socSoftware;
    satisfy tsr_309 by context.ldsda.safetyFirmware;
    satisfy tsr_311 by context.ldsda.safetyFirmware;
    satisfy tsr_401 by context.ldsda.safetyFirmware;
    satisfy tsr_402 by context.ldsda.safetyFirmware;
    satisfy tsr_403 by context.ldsda.safetyFirmware;
    satisfy tsr_404 by context.ldsda.safetyFirmware;
    satisfy tsr_405 by context.ldsda.safetyFirmware;
    satisfy tsr_406 by context.ldsda.safetyFirmware;
    satisfy tsr_407 by context.ldsda.safetyFirmware;
    satisfy tsr_408 by context.ldsda.safetyFirmware;
    satisfy tsr_409 by context.ldsda.safetyFirmware;
    satisfy tsr_409 by context.ldsda.socSoftware;
    satisfy tsr_410 by context.ldsda.safetyFirmware;
    satisfy tsr_410 by context.ldsda.socSoftware;
    satisfy tsr_411 by context.ldsda.safetyFirmware;
    satisfy tsr_412 by context.ldsda.safetyFirmware;
    satisfy tsr_413 by context.ldsda.safetyFirmware;
    satisfy tsr_501 by context.ldsda.deviceHardware.safetyMcu;
    satisfy tsr_501 by context.ldsda.safetyFirmware;
    satisfy tsr_502 by context.ldsda.safetyFirmware;
    satisfy tsr_502 by context.ldsda.deviceHardware.safetyMcu;
    satisfy tsr_503 by context.ldsda.deviceHardware.safetyMcu;
    satisfy tsr_503 by context.ldsda.safetyFirmware;
    satisfy tsr_504 by context.ldsda.deviceHardware.safetyMcu;
    satisfy tsr_504 by context.ldsda.safetyFirmware;
    satisfy tsr_505 by context.ldsda.deviceHardware.safetyMcu;
    satisfy tsr_505 by context.ldsda.safetyFirmware;
    satisfy tsr_506 by context.ldsda.deviceHardware.safetyMcu;
    satisfy tsr_506 by context.ldsda.harness;
    satisfy tsr_506 by context.ldsda.safetyFirmware;
    satisfy tsr_507 by context.ldsda.deviceHardware.safetyMcu;
    satisfy tsr_507 by context.ldsda.safetyFirmware;
    satisfy tsr_508 by context.ldsda.deviceHardware.safetyMcu;
    satisfy tsr_508 by context.ldsda.safetyFirmware;
    satisfy tsr_509 by context.ldsda.deviceHardware.safetyMcu;
    satisfy tsr_509 by context.ldsda.safetyFirmware;
    satisfy tsr_510 by context.ldsda.deviceHardware.safetyMcu;
    satisfy tsr_510 by context.ldsda.harness;
    satisfy tsr_510 by context.ldsda.safetyFirmware;
    satisfy tsr_511 by context.ldsda.safetyFirmware;
    satisfy tsr_511 by context.ldsda.deviceHardware.safetyMcu;
    satisfy tsr_511 by context.ldsda.socSoftware;
    satisfy tsr_512 by context.ldsda.safetyFirmware;
    satisfy tsr_513 by context.ldsda.safetyFirmware;
    satisfy tsr_514 by context.ldsda.safetyFirmware;
    satisfy tsr_515 by context.ldsda.safetyFirmware;
    satisfy tsr_515 by context.ldsda.deviceHardware.safetyMcu;
    satisfy tsr_516 by context.ldsda.safetyFirmware;
    satisfy tsr_516 by context.ldsda.deviceHardware.safetyMcu;
    satisfy tsr_517 by context.ldsda.safetyFirmware;
    satisfy tsr_517 by context.ldsda.deviceHardware.safetyMcu;
    satisfy tsr_518 by context.ldsda.safetyFirmware;
    satisfy tsr_519 by context.ldsda.safetyFirmware;
    satisfy tsr_519 by context.ldsda.deviceHardware.safetyMcu;
    satisfy tsr_601 by context.ldsda.socSoftware;
    satisfy tsr_602 by context.ldsda.socSoftware;
    satisfy tsr_603 by context.ldsda.socSoftware;
    satisfy tsr_604 by context.ldsda.socSoftware;
    satisfy tsr_605 by context.ldsda.socSoftware;
    satisfy tsr_606 by context.ldsda.socSoftware;
    satisfy tsr_607 by context.ldsda.socSoftware;
    satisfy tsr_608 by context.ldsda.socSoftware;
    satisfy tsr_609 by context.ldsda.socSoftware;
    satisfy tsr_610 by context.ldsda.socSoftware;
    satisfy tsr_611 by context.ldsda.socSoftware;
    satisfy tsr_612 by context.ldsda.socSoftware;
    satisfy tsr_613 by context.ldsda.socSoftware;
    satisfy tsr_614 by context.ldsda.socSoftware;
    satisfy tsr_615 by context.ldsda.socSoftware;
    satisfy tsr_616 by context.ldsda.socSoftware;
    satisfy tsr_617 by context.ldsda.socSoftware;
    satisfy tsr_618 by context.ldsda.socSoftware;
    satisfy tsr_619 by context.ldsda.socSoftware;
    satisfy tsr_620 by context.ldsda.socSoftware;
    satisfy tsr_621 by context.ldsda.socSoftware;
    satisfy tsr_622 by context.ldsda.socSoftware;
    satisfy tsr_623 by context.ldsda.socSoftware;
    satisfy tsr_624 by context.ldsda.socSoftware;
    satisfy tsr_625 by context.ldsda.socSoftware;
    satisfy tsr_626 by context.ldsda.socSoftware;
    satisfy tsr_627 by context.ldsda.socSoftware;
    satisfy tsr_628 by context.ldsda.socSoftware;
    satisfy tsr_629 by context.ldsda.socSoftware;
    satisfy tsr_630 by context.ldsda.socSoftware;
    satisfy tsr_631 by context.ldsda.socSoftware;
    satisfy tsr_632 by context.ldsda.safetyFirmware;
    satisfy tsr_633 by context.ldsda.socSoftware;
    satisfy tsr_634 by context.ldsda.socSoftware;
    satisfy tsr_635 by context.ldsda.socSoftware;
    satisfy tsr_701 by context.ldsda.deviceHardware.safetyMcu;
    satisfy tsr_701 by context.ldsda.harness;
    satisfy tsr_701 by context.ldsda.safetyFirmware;
    satisfy tsr_702 by context.ldsda.harness;
    satisfy tsr_703 by context.ldsda.harness;
    satisfy tsr_704 by context.ldsda.safetyFirmware;
    satisfy tsr_705 by context.ldsda.safetyFirmware;
    satisfy tsr_706 by context.ldsda.harness;
    satisfy tsr_706 by context.ldsda.deviceHardware.safetyMcu;
    satisfy tsr_706 by context.ldsda.safetyFirmware;
    satisfy tsr_707 by context.ldsda.safetyFirmware;
    satisfy tsr_709 by context.ldsda.socSoftware;
    satisfy tsr_710 by context.ldsda.safetyFirmware;
    satisfy tsr_711 by context.ldsda.safetyFirmware;
    satisfy tsr_712 by context.ldsda.safetyFirmware;
    satisfy tsr_712 by context.ldsda.socSoftware;
    satisfy tsr_713 by context.ldsda.socSoftware;
    satisfy sys_001 by context.ldsda.socSoftware.modeld;
    satisfy sys_001 by context.ldsda.socSoftware.controlsd;
    satisfy sys_002 by context.ldsda.socSoftware.controlsd;
    satisfy sys_003 by context.ldsda.socSoftware.controlsd;
    satisfy sys_003 by context.ldsda.socSoftware.selfdrived;
    satisfy sys_004 by context.ldsda.socSoftware.selfdrived;
    satisfy sys_004 by context.ldsda.socSoftware.hmi;
    satisfy sys_005 by context.ldsda.socSoftware.modeld;
    satisfy sys_006 by context.ldsda.socSoftware.modeld;
    satisfy sys_007 by context.ldsda.socSoftware.controlsd;
    satisfy sys_008 by context.ldsda.socSoftware.controlsd;
    satisfy sys_008 by context.ldsda.socSoftware.estimators;
    satisfy sys_020 by context.ldsda.socSoftware.plannerd;
    satisfy sys_021 by context.ldsda.socSoftware.card;
    satisfy sys_022 by context.ldsda.socSoftware.plannerd;
    satisfy sys_023 by context.ldsda.socSoftware.manager;
    satisfy sys_024 by context.ldsda.socSoftware.plannerd;
    satisfy sys_024 by context.ldsda.socSoftware.card;
    satisfy sys_025 by context.ldsda.socSoftware.card;
    satisfy sys_026 by context.ldsda.socSoftware.plannerd;
    satisfy sys_027 by context.ldsda.socSoftware.manager;
    satisfy sys_027 by context.ldsda.socSoftware.hmi;
    satisfy sys_040 by context.ldsda.socSoftware.selfdrived;
    satisfy sys_041 by context.ldsda.socSoftware.card;
    satisfy sys_042 by context.ldsda.socSoftware.selfdrived;
    satisfy sys_043 by context.ldsda.socSoftware.selfdrived;
    satisfy sys_043 by context.ldsda.socSoftware.hardwared;
    satisfy sys_060 by context.ldsda.socSoftware.dm;
    satisfy sys_061 by context.ldsda.socSoftware.dm;
    satisfy sys_062 by context.ldsda.socSoftware.dm;
    satisfy sys_063 by context.ldsda.socSoftware.dm;
    satisfy sys_063 by context.ldsda.socSoftware.controlsd;
    satisfy sys_080 by context.ldsda.socSoftware.hmi;
    satisfy sys_080 by context.ldsda.socSoftware.card;
    satisfy sys_081 by context.ldsda.socSoftware.selfdrived;
    satisfy sys_081 by context.ldsda.socSoftware.hmi;
    satisfy sys_082 by context.ldsda.socSoftware.selfdrived;
    satisfy sys_083 by context.ldsda.socSoftware.hmi;
    satisfy sys_100 by context.ldsda.socSoftware.selfdrived;
    satisfy sys_100 by context.ldsda.socSoftware.modeld;
    satisfy sys_101 by context.ldsda.socSoftware.selfdrived;
    satisfy sys_102 by context.ldsda.socSoftware.plannerd;
    satisfy sys_120 by context.ldsda.safetyFirmware.safetyLayer;
    satisfy sys_121 by context.ldsda.safetyFirmware.platformFirmware;
    satisfy sys_121 by context.ldsda.socSoftware.pandad;
    satisfy sys_140 by context.ldsda.socSoftware.remoteAndLogging;
    satisfy sys_141 by context.ldsda.socSoftware.remoteAndLogging;
    satisfy sys_142 by context.ldsda.socSoftware.remoteAndLogging;
    satisfy sys_143 by context.ldsda.socSoftware.remoteAndLogging;
    satisfy sys_144 by context.ldsda.socSoftware.remoteAndLogging;
    satisfy sys_144 by context.ldsda.socSoftware.manager;
    satisfy sys_145 by context.ldsda.socSoftware.remoteAndLogging;
    satisfy sys_145 by context.ldsda.socSoftware.hardwared;
    satisfy csr_011 by context.ldsda.safetyFirmware;
    satisfy csr_012 by context.ldsda.safetyFirmware;
    satisfy csr_013 by context.ldsda.safetyFirmware;
    satisfy csr_014 by context.ldsda.safetyFirmware;
    satisfy csr_015 by context.ldsda.safetyFirmware;
    satisfy csr_016 by context.ldsda.socSoftware;
    satisfy csr_021 by context.ldsda.safetyFirmware;
    satisfy csr_022 by context.ldsda.safetyFirmware;
    satisfy csr_023 by context.ldsda.safetyFirmware;
    satisfy csr_024 by context.ldsda.safetyFirmware;
    satisfy csr_031 by context.ldsda.safetyFirmware;
    satisfy csr_032 by context.ldsda.safetyFirmware;
    satisfy csr_033 by context.ldsda.safetyFirmware;
    satisfy csr_034 by context.ldsda.safetyFirmware;
    satisfy csr_041 by context.ldsda.safetyFirmware;
    satisfy csr_042 by context.ldsda.safetyFirmware;
    satisfy csr_051 by context.ldsda.socSoftware;
    satisfy csr_052 by context.ldsda.socSoftware;
    satisfy csr_053 by context.ldsda.socSoftware;
    satisfy csr_054 by context.ldsda.safetyFirmware;
    satisfy csr_054 by context.ldsda.socSoftware;
    satisfy csr_061 by context.ldsda.safetyFirmware;
    satisfy csr_062 by context.ldsda.socSoftware;
    satisfy csr_063 by context.ldsda.socSoftware;
    satisfy csr_064 by context.ldsda.socSoftware;
    satisfy csr_071 by context.ldsda.socSoftware;
    satisfy csr_072 by context.ldsda.socSoftware;
    satisfy csr_081 by context.ldsda.socSoftware;
    satisfy csr_082 by context.ldsda.socSoftware;
    satisfy csr_091 by context.ldsda.safetyFirmware;
    satisfy csr_092 by context.ldsda.safetyFirmware;
    satisfy csr_093 by context.ldsda.safetyFirmware;
    satisfy csr_101 by context.ldsda.socSoftware;
    satisfy csr_103 by context.ldsda.socSoftware;
    satisfy csr_104 by context.ldsda.socSoftware;
    satisfy csr_111 by context.ldsda.socSoftware;
    satisfy csr_112 by context.ldsda.socSoftware;
    satisfy csr_113 by context.ldsda.socSoftware;
    satisfy csr_114 by context.ldsda.socSoftware;
    satisfy csr_115 by context.ldsda.socSoftware;
    satisfy csr_116 by context.ldsda.socSoftware;
    satisfy csr_117 by context.ldsda.socSoftware;
    satisfy csr_121 by context.ldsda.socSoftware;
    satisfy csr_122 by context.ldsda.socSoftware;
    satisfy csr_123 by context.ldsda.socSoftware;
    satisfy csr_125 by context.ldsda.socSoftware;
    satisfy csr_141 by context.ldsda.socSoftware;
    satisfy csr_142 by context.ldsda.socSoftware;
    satisfy csr_143 by context.ldsda.socSoftware;
    satisfy csr_144 by context.ldsda.socSoftware;
    satisfy csr_151 by context.ldsda.socSoftware;
}
