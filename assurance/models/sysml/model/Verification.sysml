// GENERATED by assurance/models/sysml/tools/gen_requirements.py from the work products. Do not edit;
// change the work product and regenerate (README §7).

package LionDriverVerification {
    doc /* Test cases of the specification tables. Each verifies the modelled requirements (SG, FSR, TSR, SYS, CSR) it names. */

    private import ScalarValues::*;
    private import LionDriverRequirements::*;

    verification def VerificationCase {
        attribute spec : String;
        attribute level : String;
        attribute names : String;
        attribute steps : String[0..*];
    }
    verification <'VS-FI-01'> vs_fi_01 : VerificationCase {
        doc /* Corrupted frame (bad checksum, wrong length) */
        :>> spec = "WP-V-05 §5.1";
        :>> level = "VS-FI";
        :>> names = "SWSR-108a";
        objective {
            verify LionDriverRequirements::tsr_402;
            verify LionDriverRequirements::tsr_406;
        }
    }
    verification <'VS-FI-02'> vs_fi_02 : VerificationCase {
        doc /* Stuck / frozen payload with valid checksum */
        :>> spec = "WP-V-05 §5.1";
        :>> level = "VS-FI";
        :>> names = "SWSR-108a, SWSR-405";
        objective {
            verify LionDriverRequirements::sg_01;
            verify LionDriverRequirements::tsr_404;
            verify LionDriverRequirements::tsr_405;
            verify LionDriverRequirements::tsr_406;
        }
    }
    verification <'VS-FI-03'> vs_fi_03 : VerificationCase {
        doc /* Replayed / duplicated / inserted frames */
        :>> spec = "WP-V-05 §5.1";
        :>> level = "VS-FI";
        :>> names = "SWSR-108a";
        objective {
            verify LionDriverRequirements::tsr_403;
            verify LionDriverRequirements::tsr_406;
        }
    }
    verification <'VS-FI-04'> vs_fi_04 : VerificationCase {
        doc /* Message timeout */
        :>> spec = "WP-V-05 §5.1";
        :>> level = "VS-FI";
        :>> names = "SWSR-108a, SWSR-401, SWSR-401a";
        objective {
            verify LionDriverRequirements::tsr_401;
            verify LionDriverRequirements::tsr_406;
        }
    }
    verification <'VS-FI-05'> vs_fi_05 : VerificationCase {
        doc /* Cross-signal implausibility */
        :>> spec = "WP-V-05 §5.1";
        :>> level = "VS-FI";
        :>> names = "SWSR-405";
        objective {
            verify LionDriverRequirements::tsr_405;
        }
    }
    verification <'VS-FI-06'> vs_fi_06 : VerificationCase {
        doc /* SPI bit errors */
        :>> spec = "WP-V-05 §5.2";
        :>> level = "VS-FI";
        :>> names = "";
        objective {
            verify LionDriverRequirements::tsr_410;
            verify LionDriverRequirements::tsr_413;
        }
    }
    verification <'VS-FI-07'> vs_fi_07 : VerificationCase {
        doc /* Out-of-range length fields and indices */
        :>> spec = "WP-V-05 §5.2";
        :>> level = "VS-FI";
        :>> names = "";
        objective {
            verify LionDriverRequirements::tsr_412;
        }
    }
    verification <'VS-FI-08'> vs_fi_08 : VerificationCase {
        doc /* Stale / replayed / frozen command stream */
        :>> spec = "WP-V-05 §5.2";
        :>> level = "VS-FI";
        :>> names = "";
        objective {
            verify LionDriverRequirements::tsr_408;
            verify LionDriverRequirements::tsr_411;
        }
    }
    verification <'VS-FI-09'> vs_fi_09 : VerificationCase {
        doc /* Process kill (SIGKILL) and hang (SIGSTOP) */
        :>> spec = "WP-V-05 §5.3";
        :>> level = "VS-FI";
        :>> names = "SWSR-401a, SWSR-407, SWSR-516";
        objective {
            verify LionDriverRequirements::tsr_407;
            verify LionDriverRequirements::tsr_408;
            verify LionDriverRequirements::tsr_409;
            verify LionDriverRequirements::tsr_516;
            verify LionDriverRequirements::tsr_601;
            verify LionDriverRequirements::tsr_606;
        }
    }
    verification <'VS-FI-10'> vs_fi_10 : VerificationCase {
        doc /* Heartbeat faults */
        :>> spec = "WP-V-05 §5.2";
        :>> level = "VS-FI";
        :>> names = "SWSR-401a, SWSR-407, SWSR-516";
        objective {
            verify LionDriverRequirements::tsr_307;
            verify LionDriverRequirements::tsr_407;
            verify LionDriverRequirements::tsr_409;
            verify LionDriverRequirements::tsr_510;
            verify LionDriverRequirements::tsr_516;
        }
    }
    verification <'VS-FI-11'> vs_fi_11 : VerificationCase {
        doc /* Unauthorised configuration commands in car mode */
        :>> spec = "WP-V-05 §5.2";
        :>> level = "VS-FI";
        :>> names = "SWSR-104a, SWSR-512, SWSR-512a, SWSR-513";
        objective {
            verify LionDriverRequirements::tsr_512;
            verify LionDriverRequirements::tsr_513;
        }
    }
    verification <'VS-FI-12'> vs_fi_12 : VerificationCase {
        doc /* Stale or faulty model output */
        :>> spec = "WP-V-05 §5.3";
        :>> level = "VS-FI";
        :>> names = "";
        objective {
            verify LionDriverRequirements::tsr_601;
            verify LionDriverRequirements::tsr_602;
            verify LionDriverRequirements::tsr_603;
            verify LionDriverRequirements::tsr_616;
        }
    }
    verification <'VS-FI-13'> vs_fi_13 : VerificationCase {
        doc /* Non-finite actuator commands */
        :>> spec = "WP-V-05 §5.3";
        :>> level = "VS-FI";
        :>> names = "";
        objective {
            verify LionDriverRequirements::tsr_604;
        }
    }
    verification <'VS-FI-14'> vs_fi_14 : VerificationCase {
        doc /* Out-of-limit commands from the SoC */
        :>> spec = "WP-V-05 §5.3";
        :>> level = "VS-FI";
        :>> names = "SWSR-104a, SWSR-108a";
        objective {
            verify LionDriverRequirements::tsr_101;
            verify LionDriverRequirements::tsr_102;
            verify LionDriverRequirements::tsr_103;
            verify LionDriverRequirements::tsr_104;
            verify LionDriverRequirements::tsr_105;
            verify LionDriverRequirements::tsr_106;
            verify LionDriverRequirements::tsr_107;
            verify LionDriverRequirements::tsr_108;
            verify LionDriverRequirements::tsr_109;
            verify LionDriverRequirements::tsr_201;
            verify LionDriverRequirements::tsr_202;
            verify LionDriverRequirements::tsr_203;
            verify LionDriverRequirements::tsr_204;
            verify LionDriverRequirements::tsr_205;
        }
    }
    verification <'VS-FI-15'> vs_fi_15 : VerificationCase {
        doc /* Power dips and brown-out */
        :>> spec = "WP-V-05 §5.4";
        :>> level = "VS-FI";
        :>> names = "";
        objective {
            verify LionDriverRequirements::tsr_505;
            verify LionDriverRequirements::tsr_706;
        }
    }
    verification <'VS-FI-16'> vs_fi_16 : VerificationCase {
        doc /* Panda reset during engagement */
        :>> spec = "WP-V-05 §5.4";
        :>> level = "VS-FI";
        :>> names = "AOU-13";
        objective {
            verify LionDriverRequirements::tsr_311;
            verify LionDriverRequirements::tsr_501;
            verify LionDriverRequirements::tsr_706;
        }
    }
    verification <'VS-FI-17'> vs_fi_17 : VerificationCase {
        doc /* Panda hang */
        :>> spec = "WP-V-05 §5.4";
        :>> level = "VS-FI";
        :>> names = "SWSR-501, SWSR-501b";
        objective {
            verify LionDriverRequirements::tsr_501;
            verify LionDriverRequirements::tsr_502;
            verify LionDriverRequirements::tsr_706;
        }
    }
    verification <'VS-FI-18'> vs_fi_18 : VerificationCase {
        doc /* Memory corruption */
        :>> spec = "WP-V-05 §5.4";
        :>> level = "VS-FI";
        :>> names = "";
        objective {
            verify LionDriverRequirements::tsr_502;
            verify LionDriverRequirements::tsr_503;
            verify LionDriverRequirements::tsr_507;
        }
    }
    verification <'VS-FI-19'> vs_fi_19 : VerificationCase {
        doc /* Interrupt storm */
        :>> spec = "WP-V-05 §5.4";
        :>> level = "VS-FI";
        :>> names = "";
        objective {
            verify LionDriverRequirements::tsr_502;
            verify LionDriverRequirements::tsr_508;
        }
    }
    verification <'VS-FI-20'> vs_fi_20 : VerificationCase {
        doc /* Clock fault */
        :>> spec = "WP-V-05 §5.4";
        :>> level = "VS-FI";
        :>> names = "";
        objective {
            verify LionDriverRequirements::tsr_504;
        }
    }
    verification <'VS-FI-21'> vs_fi_21 : VerificationCase {
        doc /* Relay faults */
        :>> spec = "WP-V-05 §5.4";
        :>> level = "VS-FI";
        :>> names = "";
        objective {
            verify LionDriverRequirements::tsr_506;
            verify LionDriverRequirements::tsr_710;
        }
    }
    verification <'VS-FI-22'> vs_fi_22 : VerificationCase {
        doc /* Car-side bus-off, CAN-H/L short, error frames */
        :>> spec = "WP-V-05 §5.1";
        :>> level = "VS-FI";
        :>> names = "HWSR-508b";
        objective {
            verify LionDriverRequirements::sg_01;
            verify LionDriverRequirements::tsr_508;
        }
    }
    verification <'VS-FI-23'> vs_fi_23 : VerificationCase {
        doc /* Params tampering */
        :>> spec = "WP-V-05 §5.5";
        :>> level = "VS-FI";
        :>> names = "SWSR-104a, SWSR-512, SWSR-512a";
        objective {
            verify LionDriverRequirements::tsr_512;
            verify LionDriverRequirements::tsr_610;
            verify LionDriverRequirements::tsr_613;
            verify LionDriverRequirements::tsr_806;
        }
    }
    verification <'VS-FI-24'> vs_fi_24 : VerificationCase {
        doc /* Camera-side forwarding interruption with relay energised */
        :>> spec = "WP-V-05 §5.4";
        :>> level = "VS-FI";
        :>> names = "SWSR-513";
        objective {
            verify LionDriverRequirements::tsr_513;
            verify LionDriverRequirements::tsr_707;
        }
    }
    verification <'VS-FI-25'> vs_fi_25 : VerificationCase {
        doc /* Driver-monitoring input loss */
        :>> spec = "WP-V-05 §5.3";
        :>> level = "VS-FI";
        :>> names = "";
        objective {
            verify LionDriverRequirements::tsr_609;
        }
    }
    verification <'VS-FI-26'> vs_fi_26 : VerificationCase {
        doc /* Over-temperature */
        :>> spec = "WP-V-05 §5.4";
        :>> level = "VS-FI";
        :>> names = "";
        objective {
            verify LionDriverRequirements::tsr_509;
        }
    }
    verification <'VS-FI-27'> vs_fi_27 : VerificationCase {
        doc /* Selected faults while driving */
        :>> spec = "WP-V-05 §5.6";
        :>> level = "VS-FI";
        :>> names = "";
    }
    verification <'VS-FI-28'> vs_fi_28 : VerificationCase {
        doc /* Harness disconnect / orientation change while relay driven */
        :>> spec = "WP-V-05 §5.4";
        :>> level = "VS-FI";
        :>> names = "";
        objective {
            verify LionDriverRequirements::tsr_701;
        }
    }
    verification <'VS-FI-29'> vs_fi_29 : VerificationCase {
        doc /* Firmware integrity */
        :>> spec = "WP-V-05 §5.4";
        :>> level = "VS-FI";
        :>> names = "SWSR-511a";
        objective {
            verify LionDriverRequirements::tsr_503;
            verify LionDriverRequirements::tsr_511;
            verify LionDriverRequirements::tsr_514;
        }
    }
    verification <'VS-FI-30'> vs_fi_30 : VerificationCase {
        doc /* SoC TX flood (babbling SoC) */
        :>> spec = "WP-V-05 §5.2";
        :>> level = "VS-FI";
        :>> names = "SWSR-518";
        objective {
            verify LionDriverRequirements::tsr_518;
        }
    }
    verification <'VS-FI-31'> vs_fi_31 : VerificationCase {
        doc /* EPS fault */
        :>> spec = "WP-V-05 §5.1";
        :>> level = "VS-FI";
        :>> names = "SWSR-110, SWSR-516";
        objective {
            verify LionDriverRequirements::tsr_110;
            verify LionDriverRequirements::tsr_516;
        }
    }
    verification <'VS-FI-32'> vs_fi_32 : VerificationCase {
        doc /* Fault late in an assisted lane change (HE-01.6, DQ-406 A) */
        :>> spec = "WP-V-05 §5.6";
        :>> level = "VS-FI";
        :>> names = "HE-01.6";
        objective {
            verify LionDriverRequirements::tsr_110;
            verify LionDriverRequirements::tsr_408;
            verify LionDriverRequirements::tsr_516;
        }
    }
    verification <'VS-HW-01'> vs_hw_01 : VerificationCase {
        doc /* Relay switching and default state */
        :>> spec = "WP-H-06 §3";
        :>> level = "VS-HW";
        :>> names = "AOU-13, HWSR-502";
    }
    verification <'VS-HW-02'> vs_hw_02 : VerificationCase {
        doc /* Harness box inspection against the published v3 drawing */
        :>> spec = "WP-H-06 §3";
        :>> level = "VS-HW";
        :>> names = "HWSR-502a, HWSR-702";
    }
    verification <'VS-HW-03'> vs_hw_03 : VerificationCase {
        doc /* Relay failure detection — stuck released */
        :>> spec = "WP-H-06 §3";
        :>> level = "VS-HW";
        :>> names = "HWSR-506a";
        objective {
            verify LionDriverRequirements::fsr_01_11;
        }
    }
    verification <'VS-HW-04'> vs_hw_04 : VerificationCase {
        doc /* Relay failure detection — stuck intercepting */
        :>> spec = "WP-H-06 §3";
        :>> level = "VS-HW";
        :>> names = "HWSR-506a";
        objective {
            verify LionDriverRequirements::sg_07;
        }
    }
    verification <'VS-HW-05'> vs_hw_05 : VerificationCase {
        doc /* Debug relay command gated */
        :>> spec = "WP-H-06 §3";
        :>> level = "VS-HW";
        :>> names = "HWSR-506c";
    }
    verification <'VS-HW-06'> vs_hw_06 : VerificationCase {
        doc /* Watchdog reset behaviour (after fix) */
        :>> spec = "WP-H-06 §3";
        :>> level = "VS-HW";
        :>> names = "HWSR-501";
        objective {
            verify LionDriverRequirements::fsr_01_09;
        }
    }
    verification <'VS-HW-07'> vs_hw_07 : VerificationCase {
        doc /* Watchdog cannot be disabled */
        :>> spec = "WP-H-06 §3";
        :>> level = "VS-HW";
        :>> names = "HWSR-501c";
    }
    verification <'VS-HW-08'> vs_hw_08 : VerificationCase {
        doc /* Exception and fatal-assert paths */
        :>> spec = "WP-H-06 §3";
        :>> level = "VS-HW";
        :>> names = "HWSR-502b";
    }
    verification <'VS-HW-09'> vs_hw_09 : VerificationCase {
        doc /* Power brown-out and dropouts */
        :>> spec = "WP-H-06 §3";
        :>> level = "VS-HW";
        :>> names = "HWSR-505";
    }
    verification <'VS-HW-10'> vs_hw_10 : VerificationCase {
        doc /* Supply over-voltage (non-destructive) */
        :>> spec = "WP-H-06 §3";
        :>> level = "VS-HW";
        :>> names = "HWSR-505b";
    }
    verification <'VS-HW-11'> vs_hw_11 : VerificationCase {
        doc /* CAN bus-off and error-passive (car side) */
        :>> spec = "WP-H-06 §3";
        :>> level = "VS-HW";
        :>> names = "HWSR-508";
    }
    verification <'VS-HW-12'> vs_hw_12 : VerificationCase {
        doc /* Transceiver fault does not disturb stock path */
        :>> spec = "WP-H-06 §3";
        :>> level = "VS-HW";
        :>> names = "HWSR-508a";
    }
    verification <'VS-HW-13'> vs_hw_13 : VerificationCase {
        doc /* Harness reversed / orientation */
        :>> spec = "WP-H-06 §3";
        :>> level = "VS-HW";
        :>> names = "HWSR-701";
    }
    verification <'VS-HW-14'> vs_hw_14 : VerificationCase {
        doc /* Ignition loss and ignition-line faults */
        :>> spec = "WP-H-06 §3";
        :>> level = "VS-HW";
        :>> names = "HWSR-510";
    }
    verification <'VS-HW-15'> vs_hw_15 : VerificationCase {
        doc /* Thermal */
        :>> spec = "WP-H-06 §3";
        :>> level = "VS-HW";
        :>> names = "HWSR-509";
    }
    verification <'VS-HW-16'> vs_hw_16 : VerificationCase {
        doc /* Clock failure (analysis + test where accessible) */
        :>> spec = "WP-H-06 §3";
        :>> level = "VS-HW";
        :>> names = "HWSR-504";
    }
    verification <'VS-HW-17'> vs_hw_17 : VerificationCase {
        doc /* RAM/flash ECC and flash CRC handling */
        :>> spec = "WP-H-06 §3";
        :>> level = "VS-HW";
        :>> names = "HWSR-503";
    }
    verification <'VS-HW-18'> vs_hw_18 : VerificationCase {
        doc /* MPU */
        :>> spec = "WP-H-06 §3";
        :>> level = "VS-HW";
        :>> names = "HWSR-507";
    }
    verification <'VS-HW-19'> vs_hw_19 : VerificationCase {
        doc /* SoC reset / boot-mode control */
        :>> spec = "WP-H-06 §3";
        :>> level = "VS-HW";
        :>> names = "HWSR-502";
    }
    verification <'VS-HW-20'> vs_hw_20 : VerificationCase {
        doc /* Register divergence reaction */
        :>> spec = "WP-H-06 §3";
        :>> level = "VS-HW";
        :>> names = "HWSR-503d";
    }
    verification <'VS-HW-21'> vs_hw_21 : VerificationCase {
        doc /* SoC-independent warning (siren) */
        :>> spec = "WP-H-06 §3";
        :>> level = "VS-HW";
        :>> names = "";
        objective {
            verify LionDriverRequirements::fsr_02_05;
        }
    }
    verification <'VS-HW-22'> vs_hw_22 : VerificationCase {
        doc /* Stock path with the harness box unpowered */
        :>> spec = "WP-H-06 §3";
        :>> level = "VS-HW";
        :>> names = "HWSR-502a";
    }
    verification <'VS-HW-23'> vs_hw_23 : VerificationCase {
        doc /* Release default with the pull-down open */
        :>> spec = "WP-H-06 §3";
        :>> level = "VS-HW";
        :>> names = "HWSR-506";
    }
    verification <'VS-HW-24'> vs_hw_24 : VerificationCase {
        doc /* Switch supply stress, logic threshold and pass-through signal integrity */
        :>> spec = "WP-H-06 §3";
        :>> level = "VS-HW";
        :>> names = "HWSR-506d";
    }
    verification <'VS-ML-01'> vs_ml_01 : VerificationCase {
        doc /* Compile equivalence */
        :>> spec = "WP-W-10 §6.2";
        :>> level = "VS-ML";
        :>> names = "AIR-22, MLR-14";
    }
    verification <'VS-ML-02'> vs_ml_02 : VerificationCase {
        doc /* Structural acceptance */
        :>> spec = "WP-W-10 §6.2";
        :>> level = "VS-ML";
        :>> names = "";
    }
    verification <'VS-ML-03'> vs_ml_03 : VerificationCase {
        doc /* Scenario-sliced performance */
        :>> spec = "WP-W-10 §6.2";
        :>> level = "VS-ML";
        :>> names = "AIR-01, AIR-02, AIR-03, AIR-04, AIR-05, AIR-06, AIR-09, DSR-04";
    }
    verification <'VS-ML-04'> vs_ml_04 : VerificationCase {
        doc /* Robustness perturbations */
        :>> spec = "WP-W-10 §6.2";
        :>> level = "VS-ML";
        :>> names = "AIR-10";
    }
    verification <'VS-ML-05'> vs_ml_05 : VerificationCase {
        doc /* Uncertainty calibration */
        :>> spec = "WP-W-10 §6.2";
        :>> level = "VS-ML";
        :>> names = "AIR-13";
    }
    verification <'VS-ML-06'> vs_ml_06 : VerificationCase {
        doc /* DM evaluation */
        :>> spec = "WP-W-10 §6.2";
        :>> level = "VS-ML";
        :>> names = "AIR-07, AIR-08, AIR-15";
    }
    verification <'VS-ML-07'> vs_ml_07 : VerificationCase {
        doc /* Temporal consistency */
        :>> spec = "WP-W-10 §6.2";
        :>> level = "VS-ML";
        :>> names = "AIR-11, AIR-12";
    }
    verification <'VS-ML-08'> vs_ml_08 : VerificationCase {
        doc /* Runtime monitor effectiveness */
        :>> spec = "WP-W-10 §6.2";
        :>> level = "VS-ML";
        :>> names = "AIR-14, AIR-18";
    }
    verification <'VS-ML-09'> vs_ml_09 : VerificationCase {
        doc /* Output fault injection */
        :>> spec = "WP-W-10 §6.2";
        :>> level = "VS-ML";
        :>> names = "AIR-16, AIR-25";
    }
    verification <'VS-ML-10'> vs_ml_10 : VerificationCase {
        doc /* Timing under load */
        :>> spec = "WP-W-10 §6.2";
        :>> level = "VS-ML";
        :>> names = "AIR-17";
    }
    verification <'VS-ML-11'> vs_ml_11 : VerificationCase {
        doc /* Integrity at load */
        :>> spec = "WP-W-10 §6.2";
        :>> level = "VS-ML";
        :>> names = "AIR-19, AIR-20";
    }
    verification <'VS-ML-12'> vs_ml_12 : VerificationCase {
        doc /* Regression against previous pin */
        :>> spec = "WP-W-10 §6.2";
        :>> level = "VS-ML";
        :>> names = "AIR-24";
    }
    verification <'VS-SI-01'> vs_si_01 : VerificationCase {
        doc /* Engagement only on PCM cruise rising edge */
        :>> spec = "WP-S-08 §6.1";
        :>> level = "VS-SI";
        :>> names = "";
        :>> steps = ("I-1", "I-2", "I-4");
        objective {
            verify LionDriverRequirements::fsr_01_05;
            verify LionDriverRequirements::tsr_301;
            verify LionDriverRequirements::tsr_306;
            verify LionDriverRequirements::tsr_311;
        }
    }
    verification <'VS-SI-02'> vs_si_02 : VerificationCase {
        doc /* Disengagement on brake and cancel */
        :>> spec = "WP-S-08 §6.1";
        :>> level = "VS-SI";
        :>> names = "";
        :>> steps = ("I-1", "I-3", "I-4");
        objective {
            verify LionDriverRequirements::sg_05;
            verify LionDriverRequirements::fsr_05_01;
            verify LionDriverRequirements::fsr_05_02;
            verify LionDriverRequirements::tsr_109;
            verify LionDriverRequirements::tsr_301;
            verify LionDriverRequirements::tsr_302;
        }
    }
    verification <'VS-SI-03'> vs_si_03 : VerificationCase {
        doc /* Driver steering override */
        :>> spec = "WP-S-08 §6.1";
        :>> level = "VS-SI";
        :>> names = "";
        :>> steps = ("I-1", "I-3");
        objective {
            verify LionDriverRequirements::fsr_05_03;
            verify LionDriverRequirements::tsr_304;
        }
    }
    verification <'VS-SI-04'> vs_si_04 : VerificationCase {
        doc /* Gas override and restricted host commands in car mode */
        :>> spec = "WP-S-08 §6.1";
        :>> level = "VS-SI";
        :>> names = "";
        :>> steps = ("I-1");
        objective {
            verify LionDriverRequirements::fsr_04_04;
            verify LionDriverRequirements::fsr_05_04;
            verify LionDriverRequirements::tsr_203;
            verify LionDriverRequirements::tsr_305;
        }
    }
    verification <'VS-SI-05'> vs_si_05 : VerificationCase {
        doc /* Heartbeat loss */
        :>> spec = "WP-S-08 §6.2";
        :>> level = "VS-SI";
        :>> names = "";
        :>> steps = ("I-1", "I-2");
        objective {
            verify LionDriverRequirements::fsr_01_07;
            verify LionDriverRequirements::fsr_02_05;
            verify LionDriverRequirements::tsr_407;
            verify LionDriverRequirements::tsr_510;
            verify LionDriverRequirements::tsr_516;
        }
    }
    verification <'VS-SI-06'> vs_si_06 : VerificationCase {
        doc /* Heartbeat engaged mismatch */
        :>> spec = "WP-S-08 §6.2";
        :>> level = "VS-SI";
        :>> names = "";
        :>> steps = ("I-1");
        objective {
            verify LionDriverRequirements::fsr_01_07;
            verify LionDriverRequirements::tsr_307;
            verify LionDriverRequirements::tsr_409;
        }
    }
    verification <'VS-SI-07'> vs_si_07 : VerificationCase {
        doc /* Safety mode / param set in car mode */
        :>> spec = "WP-S-08 §6.2";
        :>> level = "VS-SI";
        :>> names = "";
        :>> steps = ("I-1");
        objective {
            verify LionDriverRequirements::fsr_01_10;
            verify LionDriverRequirements::tsr_512;
        }
    }
    verification <'VS-SI-08'> vs_si_08 : VerificationCase {
        doc /* Configuration commands in car mode */
        :>> spec = "WP-S-08 §6.2";
        :>> level = "VS-SI";
        :>> names = "";
        :>> steps = ("I-1");
        objective {
            verify LionDriverRequirements::tsr_506;
            verify LionDriverRequirements::tsr_513;
        }
    }
    verification <'VS-SI-09'> vs_si_09 : VerificationCase {
        doc /* SPI corruption */
        :>> spec = "WP-S-08 §6.2";
        :>> level = "VS-SI";
        :>> names = "";
        :>> steps = ("I-2");
        objective {
            verify LionDriverRequirements::fsr_01_08;
            verify LionDriverRequirements::tsr_410;
            verify LionDriverRequirements::tsr_412;
            verify LionDriverRequirements::tsr_413;
        }
    }
    verification <'VS-SI-10'> vs_si_10 : VerificationCase {
        doc /* Stale / replayed command stream */
        :>> spec = "WP-S-08 §6.2";
        :>> level = "VS-SI";
        :>> names = "";
        :>> steps = ("I-1");
        objective {
            verify LionDriverRequirements::fsr_01_07;
            verify LionDriverRequirements::fsr_01_08;
            verify LionDriverRequirements::tsr_408;
            verify LionDriverRequirements::tsr_410;
            verify LionDriverRequirements::tsr_411;
        }
    }
    verification <'VS-SI-11'> vs_si_11 : VerificationCase {
        doc /* TX flooding (babbling SoC) */
        :>> spec = "WP-S-08 §6.2";
        :>> level = "VS-SI";
        :>> names = "";
        :>> steps = ("I-1");
        objective {
            verify LionDriverRequirements::fsr_01_08;
            verify LionDriverRequirements::tsr_502;
            verify LionDriverRequirements::tsr_518;
        }
    }
    verification <'VS-SI-12'> vs_si_12 : VerificationCase {
        doc /* RX timeout per gating signal */
        :>> spec = "WP-S-08 §6.3";
        :>> level = "VS-SI";
        :>> names = "";
        :>> steps = ("I-1", "I-3");
        objective {
            verify LionDriverRequirements::fsr_01_06;
            verify LionDriverRequirements::tsr_401;
            verify LionDriverRequirements::tsr_406;
        }
    }
    verification <'VS-SI-13'> vs_si_13 : VerificationCase {
        doc /* E2E plausibility: stuck and replayed frames */
        :>> spec = "WP-S-08 §6.3";
        :>> level = "VS-SI";
        :>> names = "";
        :>> steps = ("I-1", "I-3");
        objective {
            verify LionDriverRequirements::fsr_01_06;
            verify LionDriverRequirements::tsr_403;
            verify LionDriverRequirements::tsr_404;
            verify LionDriverRequirements::tsr_405;
            verify LionDriverRequirements::tsr_406;
        }
    }
    verification <'VS-SI-14'> vs_si_14 : VerificationCase {
        doc /* Checksum and quality-flag rejection */
        :>> spec = "WP-S-08 §6.3";
        :>> level = "VS-SI";
        :>> names = "";
        :>> steps = ("I-1");
        objective {
            verify LionDriverRequirements::fsr_01_06;
            verify LionDriverRequirements::tsr_402;
            verify LionDriverRequirements::tsr_406;
        }
    }
    verification <'VS-SI-15'> vs_si_15 : VerificationCase {
        doc /* Torque magnitude, rate and measured tracking end-to-end */
        :>> spec = "WP-S-08 §6.4";
        :>> level = "VS-SI";
        :>> names = "";
        :>> steps = ("I-1", "I-3");
        objective {
            verify LionDriverRequirements::fsr_01_01;
            verify LionDriverRequirements::fsr_01_12;
            verify LionDriverRequirements::tsr_101;
            verify LionDriverRequirements::tsr_103;
            verify LionDriverRequirements::tsr_104;
            verify LionDriverRequirements::tsr_105;
            verify LionDriverRequirements::tsr_106;
            verify LionDriverRequirements::tsr_107;
            verify LionDriverRequirements::tsr_108;
            verify LionDriverRequirements::tsr_109;
        }
    }
    verification <'VS-SI-16'> vs_si_16 : VerificationCase {
        doc /* Accel bounds, inactive value, jerk */
        :>> spec = "WP-S-08 §6.4";
        :>> level = "VS-SI";
        :>> names = "";
        :>> steps = ("I-1", "I-3");
        objective {
            verify LionDriverRequirements::fsr_03_01;
            verify LionDriverRequirements::fsr_04_01;
            verify LionDriverRequirements::fsr_04_02;
            verify LionDriverRequirements::tsr_201;
            verify LionDriverRequirements::tsr_202;
            verify LionDriverRequirements::tsr_203;
            verify LionDriverRequirements::tsr_204;
            verify LionDriverRequirements::tsr_205;
            verify LionDriverRequirements::tsr_207;
        }
    }
    verification <'VS-SI-17'> vs_si_17 : VerificationCase {
        doc /* Excessive-actuation latch and host fault reactions */
        :>> spec = "WP-S-08 §6.4";
        :>> level = "VS-SI";
        :>> names = "";
        :>> steps = ("I-2", "I-3");
        objective {
            verify LionDriverRequirements::fsr_06_04;
            verify LionDriverRequirements::tsr_604;
            verify LionDriverRequirements::tsr_617;
        }
    }
    verification <'VS-SI-18'> vs_si_18 : VerificationCase {
        doc /* Relay state per mode */
        :>> spec = "WP-S-08 §6.5";
        :>> level = "VS-SI";
        :>> names = "AOU-13";
        :>> steps = ("I-1", "I-4");
        objective {
            verify LionDriverRequirements::fsr_07_03;
            verify LionDriverRequirements::tsr_506;
            verify LionDriverRequirements::tsr_702;
            verify LionDriverRequirements::tsr_706;
        }
    }
    verification <'VS-SI-19'> vs_si_19 : VerificationCase {
        doc /* Relay malfunction detection */
        :>> spec = "WP-S-08 §6.5";
        :>> level = "VS-SI";
        :>> names = "";
        :>> steps = ("I-1");
        objective {
            verify LionDriverRequirements::fsr_01_11;
            verify LionDriverRequirements::tsr_506;
            verify LionDriverRequirements::tsr_710;
        }
    }
    verification <'VS-SI-20'> vs_si_20 : VerificationCase {
        doc /* PCS message forwarding unchanged */
        :>> spec = "WP-S-08 §6.5";
        :>> level = "VS-SI";
        :>> names = "";
        :>> steps = ("I-1", "I-2", "I-4");
        objective {
            verify LionDriverRequirements::fsr_07_01;
            verify LionDriverRequirements::tsr_704;
            verify LionDriverRequirements::tsr_707;
        }
    }
    verification <'VS-SI-21'> vs_si_21 : VerificationCase {
        doc /* PCS masquerade from SoC */
        :>> spec = "WP-S-08 §6.5";
        :>> level = "VS-SI";
        :>> names = "";
        :>> steps = ("I-1");
        objective {
            verify LionDriverRequirements::fsr_07_02;
            verify LionDriverRequirements::tsr_705;
        }
    }
    verification <'VS-SI-22'> vs_si_22 : VerificationCase {
        doc /* Soft disable on stale inputs */
        :>> spec = "WP-S-08 §6.6";
        :>> level = "VS-SI";
        :>> names = "";
        :>> steps = ("I-2", "I-3");
        objective {
            verify LionDriverRequirements::fsr_02_02;
            verify LionDriverRequirements::fsr_02_03;
            verify LionDriverRequirements::fsr_06_02;
            verify LionDriverRequirements::tsr_601;
            verify LionDriverRequirements::tsr_602;
            verify LionDriverRequirements::tsr_606;
        }
    }
    verification <'VS-SI-23'> vs_si_23 : VerificationCase {
        doc /* SoC process kill / hang */
        :>> spec = "WP-S-08 §6.6";
        :>> level = "VS-SI";
        :>> names = "";
        :>> steps = ("I-2");
        objective {
            verify LionDriverRequirements::fsr_01_07;
            verify LionDriverRequirements::fsr_02_05;
            verify LionDriverRequirements::tsr_407;
            verify LionDriverRequirements::tsr_408;
            verify LionDriverRequirements::tsr_516;
            verify LionDriverRequirements::tsr_601;
        }
    }
    verification <'VS-SI-24'> vs_si_24 : VerificationCase {
        doc /* Cruise mismatch reaction */
        :>> spec = "WP-S-08 §6.6";
        :>> level = "VS-SI";
        :>> names = "";
        :>> steps = ("I-2");
        objective {
            verify LionDriverRequirements::fsr_05_06;
            verify LionDriverRequirements::tsr_307;
            verify LionDriverRequirements::tsr_308;
        }
    }
    verification <'VS-SI-25'> vs_si_25 : VerificationCase {
        doc /* MCU reset during engagement */
        :>> spec = "WP-S-08 §6.6";
        :>> level = "VS-SI";
        :>> names = "AOU-13";
        :>> steps = ("I-1", "I-2");
        objective {
            verify LionDriverRequirements::fsr_01_09;
            verify LionDriverRequirements::fsr_07_03;
            verify LionDriverRequirements::tsr_311;
            verify LionDriverRequirements::tsr_706;
        }
    }
    verification <'VS-SI-26'> vs_si_26 : VerificationCase {
        doc /* Target vs host safety model; process replay regression */
        :>> spec = "WP-S-08 §6.7";
        :>> level = "VS-SI";
        :>> names = "";
        :>> steps = ("I-1", "I-2");
        objective {
            verify LionDriverRequirements::fsr_01_01;
            verify LionDriverRequirements::fsr_01_02;
            verify LionDriverRequirements::fsr_01_03;
            verify LionDriverRequirements::fsr_01_04;
            verify LionDriverRequirements::fsr_01_05;
            verify LionDriverRequirements::fsr_01_06;
            verify LionDriverRequirements::fsr_01_07;
            verify LionDriverRequirements::fsr_01_08;
            verify LionDriverRequirements::fsr_01_09;
            verify LionDriverRequirements::fsr_01_10;
            verify LionDriverRequirements::fsr_01_11;
            verify LionDriverRequirements::fsr_01_12;
            verify LionDriverRequirements::fsr_01_13;
            verify LionDriverRequirements::fsr_01_14;
            verify LionDriverRequirements::fsr_02_01;
            verify LionDriverRequirements::fsr_02_02;
            verify LionDriverRequirements::fsr_02_03;
            verify LionDriverRequirements::fsr_02_04;
            verify LionDriverRequirements::fsr_02_05;
            verify LionDriverRequirements::fsr_02_06;
            verify LionDriverRequirements::fsr_02_07;
            verify LionDriverRequirements::fsr_02_08;
            verify LionDriverRequirements::fsr_02_09;
            verify LionDriverRequirements::fsr_02_10;
            verify LionDriverRequirements::fsr_02_11;
            verify LionDriverRequirements::fsr_02_12;
            verify LionDriverRequirements::fsr_03_01;
            verify LionDriverRequirements::fsr_03_02;
            verify LionDriverRequirements::fsr_03_03;
            verify LionDriverRequirements::fsr_03_04;
            verify LionDriverRequirements::fsr_03_05;
            verify LionDriverRequirements::fsr_03_06;
            verify LionDriverRequirements::fsr_04_01;
            verify LionDriverRequirements::fsr_04_02;
            verify LionDriverRequirements::fsr_04_03;
            verify LionDriverRequirements::fsr_04_04;
            verify LionDriverRequirements::fsr_04_05;
            verify LionDriverRequirements::fsr_04_06;
            verify LionDriverRequirements::fsr_05_01;
            verify LionDriverRequirements::fsr_05_02;
            verify LionDriverRequirements::fsr_05_03;
            verify LionDriverRequirements::fsr_05_04;
            verify LionDriverRequirements::fsr_05_05;
            verify LionDriverRequirements::fsr_05_06;
            verify LionDriverRequirements::fsr_05_07;
            verify LionDriverRequirements::fsr_06_01;
            verify LionDriverRequirements::fsr_06_02;
            verify LionDriverRequirements::fsr_06_03;
            verify LionDriverRequirements::fsr_06_04;
            verify LionDriverRequirements::fsr_06_05;
            verify LionDriverRequirements::fsr_07_01;
            verify LionDriverRequirements::fsr_07_02;
            verify LionDriverRequirements::fsr_07_03;
            verify LionDriverRequirements::fsr_07_04;
            verify LionDriverRequirements::fsr_07_05;
            verify LionDriverRequirements::fsr_07_06;
            verify LionDriverRequirements::fsr_07_07;
            verify LionDriverRequirements::tsr_101;
            verify LionDriverRequirements::tsr_102;
            verify LionDriverRequirements::tsr_103;
            verify LionDriverRequirements::tsr_104;
            verify LionDriverRequirements::tsr_105;
            verify LionDriverRequirements::tsr_106;
            verify LionDriverRequirements::tsr_107;
            verify LionDriverRequirements::tsr_108;
            verify LionDriverRequirements::tsr_109;
            verify LionDriverRequirements::tsr_110;
            verify LionDriverRequirements::tsr_111;
            verify LionDriverRequirements::tsr_201;
            verify LionDriverRequirements::tsr_202;
            verify LionDriverRequirements::tsr_203;
            verify LionDriverRequirements::tsr_204;
            verify LionDriverRequirements::tsr_205;
            verify LionDriverRequirements::tsr_206;
            verify LionDriverRequirements::tsr_207;
            verify LionDriverRequirements::tsr_208;
            verify LionDriverRequirements::tsr_301;
            verify LionDriverRequirements::tsr_302;
            verify LionDriverRequirements::tsr_303;
            verify LionDriverRequirements::tsr_304;
            verify LionDriverRequirements::tsr_305;
            verify LionDriverRequirements::tsr_306;
            verify LionDriverRequirements::tsr_307;
            verify LionDriverRequirements::tsr_308;
            verify LionDriverRequirements::tsr_309;
            verify LionDriverRequirements::tsr_310;
            verify LionDriverRequirements::tsr_311;
        }
    }
    verification <'VS-SI-27'> vs_si_27 : VerificationCase {
        doc /* Host reaction to envelope reports */
        :>> spec = "WP-S-08 §6.7";
        :>> level = "VS-SI";
        :>> names = "SWSR-307h";
        :>> steps = ("I-2");
        objective {
            verify LionDriverRequirements::tsr_307;
            verify LionDriverRequirements::tsr_514;
            verify LionDriverRequirements::tsr_601;
            verify LionDriverRequirements::tsr_606;
            verify LionDriverRequirements::tsr_615;
            verify LionDriverRequirements::tsr_619;
            verify LionDriverRequirements::tsr_620;
        }
    }
    verification <'VS-SQ-01'> vs_sq_01 : VerificationCase {
        doc /* EPS LKA torque authority */
        :>> spec = "WP-S-09 §5.1";
        :>> level = "VS-SQ";
        :>> names = "";
        objective {
            verify LionDriverRequirements::fsr_01_13;
            verify LionDriverRequirements::tsr_102;
            verify LionDriverRequirements::tsr_111;
        }
    }
    verification <'VS-SQ-02'> vs_sq_02 : VerificationCase {
        doc /* EPS timeout and request-bit behaviour */
        :>> spec = "WP-S-09 §5.1";
        :>> level = "VS-SQ";
        :>> names = "";
        objective {
            verify LionDriverRequirements::fsr_01_13;
            verify LionDriverRequirements::tsr_109;
            verify LionDriverRequirements::tsr_111;
        }
    }
    verification <'VS-SQ-03'> vs_sq_03 : VerificationCase {
        doc /* Envelope-bounded worst case: lateral deviation */
        :>> spec = "WP-S-09 §5.1";
        :>> level = "VS-SQ";
        :>> names = "";
        objective {
            verify LionDriverRequirements::sg_01;
            verify LionDriverRequirements::fsr_01_01;
            verify LionDriverRequirements::fsr_01_02;
            verify LionDriverRequirements::tsr_101;
            verify LionDriverRequirements::tsr_102;
            verify LionDriverRequirements::tsr_103;
        }
    }
    verification <'VS-SQ-04'> vs_sq_04 : VerificationCase {
        doc /* Brake override */
        :>> spec = "WP-S-09 §5.1";
        :>> level = "VS-SQ";
        :>> names = "";
        objective {
            verify LionDriverRequirements::fsr_05_01;
            verify LionDriverRequirements::fsr_05_07;
            verify LionDriverRequirements::tsr_302;
            verify LionDriverRequirements::tsr_310;
        }
    }
    verification <'VS-SQ-05'> vs_sq_05 : VerificationCase {
        doc /* PCM ACC envelope and cancel */
        :>> spec = "WP-S-09 §5.1";
        :>> level = "VS-SQ";
        :>> names = "";
        objective {
            verify LionDriverRequirements::fsr_03_06;
            verify LionDriverRequirements::fsr_04_02;
            verify LionDriverRequirements::fsr_04_03;
            verify LionDriverRequirements::tsr_206;
            verify LionDriverRequirements::tsr_208;
        }
    }
    verification <'VS-SQ-06'> vs_sq_06 : VerificationCase {
        doc /* Stock PCS preserved */
        :>> spec = "WP-S-09 §5.1";
        :>> level = "VS-SQ";
        :>> names = "";
        objective {
            verify LionDriverRequirements::sg_07;
            verify LionDriverRequirements::fsr_07_01;
            verify LionDriverRequirements::fsr_07_04;
            verify LionDriverRequirements::fsr_07_05;
            verify LionDriverRequirements::tsr_704;
            verify LionDriverRequirements::tsr_708;
            verify LionDriverRequirements::tsr_709;
        }
    }
    verification <'VS-SQ-07'> vs_sq_07 : VerificationCase {
        doc /* Cluster cruise indication independence */
        :>> spec = "WP-S-09 §5.1";
        :>> level = "VS-SQ";
        :>> names = "AOU-12";
        objective {
            verify LionDriverRequirements::fsr_05_05;
            verify LionDriverRequirements::tsr_309;
        }
    }
    verification <'VS-SQ-08'> vs_sq_08 : VerificationCase {
        doc /* Engagement and disengagement end-to-end */
        :>> spec = "WP-S-09 §5.2";
        :>> level = "VS-SQ";
        :>> names = "";
        objective {
            verify LionDriverRequirements::fsr_01_05;
            verify LionDriverRequirements::fsr_05_01;
            verify LionDriverRequirements::fsr_05_02;
            verify LionDriverRequirements::fsr_05_05;
            verify LionDriverRequirements::tsr_301;
            verify LionDriverRequirements::tsr_302;
            verify LionDriverRequirements::tsr_303;
            verify LionDriverRequirements::tsr_309;
            verify LionDriverRequirements::sys_040;
            verify LionDriverRequirements::sys_041;
            verify LionDriverRequirements::sys_042;
            verify LionDriverRequirements::sys_080;
        }
    }
    verification <'VS-SQ-09'> vs_sq_09 : VerificationCase {
        doc /* Gas override */
        :>> spec = "WP-S-09 §5.2";
        :>> level = "VS-SQ";
        :>> names = "";
        objective {
            verify LionDriverRequirements::fsr_04_04;
            verify LionDriverRequirements::fsr_05_04;
            verify LionDriverRequirements::tsr_203;
            verify LionDriverRequirements::tsr_305;
            verify LionDriverRequirements::sys_042;
        }
    }
    verification <'VS-SQ-10'> vs_sq_10 : VerificationCase {
        doc /* Steering override */
        :>> spec = "WP-S-09 §5.2";
        :>> level = "VS-SQ";
        :>> names = "";
        objective {
            verify LionDriverRequirements::fsr_05_03;
            verify LionDriverRequirements::tsr_304;
        }
    }
    verification <'VS-SQ-11'> vs_sq_11 : VerificationCase {
        doc /* Accel / decel limits and jerk on vehicle */
        :>> spec = "WP-S-09 §5.2";
        :>> level = "VS-SQ";
        :>> names = "";
        objective {
            verify LionDriverRequirements::fsr_03_01;
            verify LionDriverRequirements::fsr_04_01;
            verify LionDriverRequirements::fsr_04_02;
            verify LionDriverRequirements::tsr_201;
            verify LionDriverRequirements::tsr_202;
            verify LionDriverRequirements::tsr_203;
            verify LionDriverRequirements::tsr_204;
            verify LionDriverRequirements::tsr_205;
            verify LionDriverRequirements::sys_022;
            verify LionDriverRequirements::sys_024;
            verify LionDriverRequirements::sys_026;
        }
    }
    verification <'VS-SQ-12'> vs_sq_12 : VerificationCase {
        doc /* SoC loss while driving */
        :>> spec = "WP-S-09 §5.2";
        :>> level = "VS-SQ";
        :>> names = "";
        objective {
            verify LionDriverRequirements::sg_02;
            verify LionDriverRequirements::fsr_01_07;
            verify LionDriverRequirements::fsr_02_05;
            verify LionDriverRequirements::tsr_407;
            verify LionDriverRequirements::tsr_408;
            verify LionDriverRequirements::tsr_510;
            verify LionDriverRequirements::tsr_516;
        }
    }
    verification <'VS-SQ-13'> vs_sq_13 : VerificationCase {
        doc /* Fault-induced lateral safe-state transition in a curve */
        :>> spec = "WP-S-09 §5.2";
        :>> level = "VS-SQ";
        :>> names = "HE-02.1";
        objective {
            verify LionDriverRequirements::fsr_02_03;
            verify LionDriverRequirements::fsr_02_04;
            verify LionDriverRequirements::tsr_109;
            verify LionDriverRequirements::tsr_601;
            verify LionDriverRequirements::tsr_606;
            verify LionDriverRequirements::sys_081;
            verify LionDriverRequirements::sys_082;
        }
    }
    verification <'VS-SQ-14'> vs_sq_14 : VerificationCase {
        doc /* Longitudinal safe-state transition */
        :>> spec = "WP-S-09 §5.2";
        :>> level = "VS-SQ";
        :>> names = "";
        objective {
            verify LionDriverRequirements::fsr_04_03;
            verify LionDriverRequirements::fsr_06_02;
            verify LionDriverRequirements::tsr_206;
            verify LionDriverRequirements::tsr_601;
            verify LionDriverRequirements::tsr_606;
            verify LionDriverRequirements::sys_081;
        }
    }
    verification <'VS-SQ-15'> vs_sq_15 : VerificationCase {
        doc /* Driver monitoring escalation and lockout */
        :>> spec = "WP-S-09 §5.2";
        :>> level = "VS-SQ";
        :>> names = "";
        objective {
            verify LionDriverRequirements::fsr_02_06;
            verify LionDriverRequirements::tsr_608;
            verify LionDriverRequirements::tsr_609;
            verify LionDriverRequirements::tsr_610;
            verify LionDriverRequirements::tsr_611;
            verify LionDriverRequirements::tsr_612;
            verify LionDriverRequirements::sys_060;
            verify LionDriverRequirements::sys_062;
            verify LionDriverRequirements::sys_063;
        }
    }
    verification <'VS-SQ-16'> vs_sq_16 : VerificationCase {
        doc /* Process replay regression */
        :>> spec = "WP-S-09 §5.3";
        :>> level = "VS-SQ";
        :>> names = "";
        objective {
            verify LionDriverRequirements::tsr_601;
            verify LionDriverRequirements::tsr_602;
            verify LionDriverRequirements::tsr_603;
            verify LionDriverRequirements::tsr_604;
            verify LionDriverRequirements::tsr_605;
            verify LionDriverRequirements::tsr_606;
            verify LionDriverRequirements::tsr_607;
            verify LionDriverRequirements::tsr_608;
            verify LionDriverRequirements::tsr_609;
            verify LionDriverRequirements::tsr_610;
            verify LionDriverRequirements::tsr_611;
            verify LionDriverRequirements::tsr_612;
            verify LionDriverRequirements::tsr_613;
            verify LionDriverRequirements::tsr_614;
            verify LionDriverRequirements::tsr_615;
            verify LionDriverRequirements::tsr_616;
            verify LionDriverRequirements::tsr_617;
            verify LionDriverRequirements::tsr_618;
            verify LionDriverRequirements::sys_001;
            verify LionDriverRequirements::sys_002;
            verify LionDriverRequirements::sys_003;
            verify LionDriverRequirements::sys_004;
            verify LionDriverRequirements::sys_007;
            verify LionDriverRequirements::sys_008;
            verify LionDriverRequirements::sys_020;
            verify LionDriverRequirements::sys_021;
            verify LionDriverRequirements::sys_022;
            verify LionDriverRequirements::sys_023;
            verify LionDriverRequirements::sys_024;
            verify LionDriverRequirements::sys_025;
            verify LionDriverRequirements::sys_026;
        }
    }
    verification <'VS-SQ-17'> vs_sq_17 : VerificationCase {
        doc /* Safety replay of the full Corolla log set */
        :>> spec = "WP-S-09 §5.3";
        :>> level = "VS-SQ";
        :>> names = "";
        objective {
            verify LionDriverRequirements::fsr_01_01;
            verify LionDriverRequirements::fsr_01_02;
            verify LionDriverRequirements::fsr_01_03;
            verify LionDriverRequirements::fsr_01_04;
            verify LionDriverRequirements::fsr_01_05;
            verify LionDriverRequirements::fsr_01_06;
            verify LionDriverRequirements::fsr_01_07;
            verify LionDriverRequirements::fsr_01_08;
            verify LionDriverRequirements::fsr_01_09;
            verify LionDriverRequirements::fsr_01_10;
            verify LionDriverRequirements::fsr_01_11;
            verify LionDriverRequirements::fsr_01_12;
            verify LionDriverRequirements::fsr_01_13;
            verify LionDriverRequirements::fsr_01_14;
            verify LionDriverRequirements::fsr_02_01;
            verify LionDriverRequirements::fsr_02_02;
            verify LionDriverRequirements::fsr_02_03;
            verify LionDriverRequirements::fsr_02_04;
            verify LionDriverRequirements::fsr_02_05;
            verify LionDriverRequirements::fsr_02_06;
            verify LionDriverRequirements::fsr_02_07;
            verify LionDriverRequirements::fsr_02_08;
            verify LionDriverRequirements::fsr_02_09;
            verify LionDriverRequirements::fsr_02_10;
            verify LionDriverRequirements::fsr_02_11;
            verify LionDriverRequirements::fsr_02_12;
            verify LionDriverRequirements::fsr_03_01;
            verify LionDriverRequirements::fsr_03_02;
            verify LionDriverRequirements::fsr_03_03;
            verify LionDriverRequirements::fsr_03_04;
            verify LionDriverRequirements::fsr_03_05;
            verify LionDriverRequirements::fsr_03_06;
            verify LionDriverRequirements::fsr_04_01;
            verify LionDriverRequirements::fsr_04_02;
            verify LionDriverRequirements::fsr_04_03;
            verify LionDriverRequirements::fsr_04_04;
            verify LionDriverRequirements::fsr_04_05;
            verify LionDriverRequirements::fsr_04_06;
            verify LionDriverRequirements::fsr_05_01;
            verify LionDriverRequirements::fsr_05_02;
            verify LionDriverRequirements::fsr_05_03;
            verify LionDriverRequirements::fsr_05_04;
            verify LionDriverRequirements::fsr_05_05;
            verify LionDriverRequirements::fsr_05_06;
            verify LionDriverRequirements::fsr_05_07;
            verify LionDriverRequirements::fsr_06_01;
            verify LionDriverRequirements::fsr_06_02;
            verify LionDriverRequirements::fsr_06_03;
            verify LionDriverRequirements::fsr_06_04;
            verify LionDriverRequirements::fsr_06_05;
            verify LionDriverRequirements::fsr_07_01;
            verify LionDriverRequirements::fsr_07_02;
            verify LionDriverRequirements::fsr_07_03;
            verify LionDriverRequirements::fsr_07_04;
            verify LionDriverRequirements::fsr_07_05;
            verify LionDriverRequirements::fsr_07_06;
            verify LionDriverRequirements::fsr_07_07;
            verify LionDriverRequirements::tsr_101;
            verify LionDriverRequirements::tsr_102;
            verify LionDriverRequirements::tsr_103;
            verify LionDriverRequirements::tsr_104;
            verify LionDriverRequirements::tsr_105;
            verify LionDriverRequirements::tsr_106;
            verify LionDriverRequirements::tsr_107;
            verify LionDriverRequirements::tsr_108;
            verify LionDriverRequirements::tsr_109;
            verify LionDriverRequirements::tsr_110;
            verify LionDriverRequirements::tsr_201;
            verify LionDriverRequirements::tsr_202;
            verify LionDriverRequirements::tsr_203;
            verify LionDriverRequirements::tsr_204;
            verify LionDriverRequirements::tsr_205;
            verify LionDriverRequirements::tsr_206;
            verify LionDriverRequirements::tsr_207;
            verify LionDriverRequirements::tsr_301;
            verify LionDriverRequirements::tsr_302;
            verify LionDriverRequirements::tsr_303;
            verify LionDriverRequirements::tsr_304;
            verify LionDriverRequirements::tsr_305;
            verify LionDriverRequirements::tsr_306;
            verify LionDriverRequirements::tsr_307;
            verify LionDriverRequirements::tsr_308;
            verify LionDriverRequirements::tsr_309;
            verify LionDriverRequirements::tsr_310;
            verify LionDriverRequirements::tsr_311;
            verify LionDriverRequirements::tsr_401;
            verify LionDriverRequirements::tsr_402;
            verify LionDriverRequirements::tsr_403;
            verify LionDriverRequirements::tsr_404;
            verify LionDriverRequirements::tsr_405;
            verify LionDriverRequirements::tsr_406;
        }
    }
    verification <'VS-SQ-18'> vs_sq_18 : VerificationCase {
        doc /* Controller margin to envelope */
        :>> spec = "WP-S-09 §5.3";
        :>> level = "VS-SQ";
        :>> names = "";
        objective {
            verify LionDriverRequirements::fsr_01_14;
            verify LionDriverRequirements::tsr_605;
            verify LionDriverRequirements::sys_120;
        }
    }
    verification <'VS-SQ-19'> vs_sq_19 : VerificationCase {
        doc /* Supervised endurance drive */
        :>> spec = "WP-S-09 §5.4";
        :>> level = "VS-SQ";
        :>> names = "";
        objective {
            verify LionDriverRequirements::sys_001;
            verify LionDriverRequirements::sys_003;
            verify LionDriverRequirements::sys_004;
            verify LionDriverRequirements::sys_008;
            verify LionDriverRequirements::sys_020;
            verify LionDriverRequirements::sys_022;
            verify LionDriverRequirements::sys_081;
            verify LionDriverRequirements::sys_120;
            verify LionDriverRequirements::sys_140;
            verify LionDriverRequirements::sys_141;
        }
    }
    verification <'VS-SQ-20'> vs_sq_20 : VerificationCase {
        doc /* Start-up fault-code read, per ECU */
        :>> spec = "WP-S-09 §5.2";
        :>> level = "VS-SQ";
        :>> names = "AOU-09, AOU-10, SWSR-629";
        objective {
            verify LionDriverRequirements::fsr_02_12;
            verify LionDriverRequirements::tsr_629;
        }
    }
    verification <'VS-SWI-01'> vs_swi_01 : VerificationCase {
        doc /* Actuation path across units: SoC frame → TX hook → limits → accept/reject; lateral and longitudinal; substitute zero-torque frame after rejection */
        :>> spec = "WP-W-07 §5";
        :>> level = "VS-SWI";
        :>> names = "SWSR-101, SWSR-102, SWSR-103, SWSR-104, SWSR-105, SWSR-106, SWSR-107, SWSR-108, SWSR-109, SWSR-201, SWSR-202, SWSR-203, SWSR-204, SWSR-205, SWSR-206, SWSR-207";
    }
    verification <'VS-SWI-02'> vs_swi_02 : VerificationCase {
        doc /* Engagement chain: RX frames (0x1D2, 0x226, 0xAA, 0x260) → authority → TX acceptance */
        :>> spec = "WP-W-07 §5";
        :>> level = "VS-SWI";
        :>> names = "SWSR-301, SWSR-302, SWSR-304, SWSR-305, SWSR-306, SWSR-311";
    }
    verification <'VS-SWI-03'> vs_swi_03 : VerificationCase {
        doc /* RX check integration: forwarding before RX validation, checksum failure, quality flag, whitelisting */
        :>> spec = "WP-W-07 §5";
        :>> level = "VS-SWI";
        :>> names = "SWSR-402, SWSR-406, SWSR-704";
    }
    verification <'VS-SWI-04'> vs_swi_04 : VerificationCase {
        doc /* RX timeout through the periodic task */
        :>> spec = "WP-W-07 §5";
        :>> level = "VS-SWI";
        :>> names = "SWSR-306, SWSR-401, SWSR-401a";
    }
    verification <'VS-SWI-05'> vs_swi_05 : VerificationCase {
        doc /* Heartbeat path 0xf3 → tick/safety task */
        :>> spec = "WP-W-07 §5";
        :>> level = "VS-SWI";
        :>> names = "SWSR-307, SWSR-407, SWSR-409, SWSR-510";
    }
    verification <'VS-SWI-06'> vs_swi_06 : VerificationCase {
        doc /* Command freshness */
        :>> spec = "WP-W-07 §5";
        :>> level = "VS-SWI";
        :>> names = "SWSR-109a, SWSR-408";
    }
    verification <'VS-SWI-07'> vs_swi_07 : VerificationCase {
        doc /* SPI corruption */
        :>> spec = "WP-W-07 §5";
        :>> level = "VS-SWI";
        :>> names = "SWSR-410, SWSR-410a, SWSR-410b, SWSR-413";
    }
    verification <'VS-SWI-08'> vs_swi_08 : VerificationCase {
        doc /* SPI length and index bounds (fuzz) */
        :>> spec = "WP-W-07 §5";
        :>> level = "VS-SWI";
        :>> names = "SWSR-412, SWSR-412a, SWSR-412b";
    }
    verification <'VS-SWI-09'> vs_swi_09 : VerificationCase {
        doc /* Forwarding and relay malfunction interplay */
        :>> spec = "WP-W-07 §5";
        :>> level = "VS-SWI";
        :>> names = "SWSR-506a, SWSR-704, SWSR-705, SWSR-707, SWSR-710";
    }
    verification <'VS-SWI-10'> vs_swi_10 : VerificationCase {
        doc /* Mode-set sequence SILENT → NOOUTPUT → ELM327 → TOYOTA/73, and lock */
        :>> spec = "WP-W-07 §5";
        :>> level = "VS-SWI";
        :>> names = "SWSR-104a, SWSR-311, SWSR-512";
    }
    verification <'VS-SWI-11'> vs_swi_11 : VerificationCase {
        doc /* Queue overflow */
        :>> spec = "WP-W-07 §5";
        :>> level = "VS-SWI";
        :>> names = "SWSR-502b, SWSR-707";
    }
    verification <'VS-SWI-12'> vs_swi_12 : VerificationCase {
        doc /* ISR load and priority scheme */
        :>> spec = "WP-W-07 §5";
        :>> level = "VS-SWI";
        :>> names = "SWSR-401a, SWSR-501, SWSR-502b, SWSR-519";
    }
    verification <'VS-SWI-13'> vs_swi_13 : VerificationCase {
        doc /* Fault reaction integration */
        :>> spec = "WP-W-07 §5";
        :>> level = "VS-SWI";
        :>> names = "SWSR-502, SWSR-502a, SWSR-503a, SWSR-516";
    }
    verification <'VS-SWI-14'> vs_swi_14 : VerificationCase {
        doc /* Control-request gating in car mode */
        :>> spec = "WP-W-07 §5";
        :>> level = "VS-SWI";
        :>> names = "SWSR-511a, SWSR-513";
    }
    verification <'VS-SWI-15'> vs_swi_15 : VerificationCase {
        doc /* Resource usage */
        :>> spec = "WP-W-07 §5";
        :>> level = "VS-SWI";
        :>> names = "";
    }
    verification <'VS-SWI-16'> vs_swi_16 : VerificationCase {
        doc /* pandad ↔ firmware interface */
        :>> spec = "WP-W-07 §5";
        :>> level = "VS-SWI";
        :>> names = "SWSR-409h, SWSR-410h, SWSR-414h, SWSR-514h, SWSR-619";
    }
    verification <'VS-SWI-17'> vs_swi_17 : VerificationCase {
        doc /* Host reaction chain: health → pandaStates → selfdrived */
        :>> spec = "WP-W-07 §5";
        :>> level = "VS-SWI";
        :>> names = "SWSR-307h, SWSR-601, SWSR-606, SWSR-615";
    }
    verification <'VS-SWI-18'> vs_swi_18 : VerificationCase {
        doc /* Replay of fork-owned reference drives through the release libsafety */
        :>> spec = "WP-W-07 §5";
        :>> level = "VS-SWI";
        :>> names = "SWSR-101, SWSR-102, SWSR-103, SWSR-104, SWSR-105, SWSR-106, SWSR-107, SWSR-108, SWSR-109, SWSR-110, SWSR-201, SWSR-202, SWSR-203, SWSR-204, SWSR-205, SWSR-206, SWSR-207, SWSR-401, SWSR-402, SWSR-403, SWSR-404, SWSR-405, SWSR-406";
    }
    verification <'VS-SWI-19'> vs_swi_19 : VerificationCase {
        doc /* Per-ID TX rate supervision and TX read-back */
        :>> spec = "WP-W-07 §5";
        :>> level = "VS-SWI";
        :>> names = "SWSR-517, SWSR-518";
    }
    verification <'VS-SWQ-01'> vs_swq_01 : VerificationCase {
        doc /* Torque magnitude limit on target */
        :>> spec = "WP-W-08 §5";
        :>> level = "VS-SWQ";
        :>> names = "SWSR-101, SWSR-101a, SWSR-102";
    }
    verification <'VS-SWQ-02'> vs_swq_02 : VerificationCase {
        doc /* Rate and RT window */
        :>> spec = "WP-W-08 §5";
        :>> level = "VS-SWQ";
        :>> names = "SWSR-103, SWSR-103a";
    }
    verification <'VS-SWQ-03'> vs_swq_03 : VerificationCase {
        doc /* Measured-torque tracking with plant */
        :>> spec = "WP-W-08 §5";
        :>> level = "VS-SWQ";
        :>> names = "SWSR-104, SWSR-104a";
    }
    verification <'VS-SWQ-04'> vs_swq_04 : VerificationCase {
        doc /* Gating, steer-request rules, latch and safe-state frames */
        :>> spec = "WP-W-08 §5";
        :>> level = "VS-SWQ";
        :>> names = "SWSR-105, SWSR-106, SWSR-107, SWSR-108, SWSR-109, SWSR-109a";
    }
    verification <'VS-SWQ-05'> vs_swq_05 : VerificationCase {
        doc /* Longitudinal limits and fields */
        :>> spec = "WP-W-08 §5";
        :>> level = "VS-SWQ";
        :>> names = "SWSR-201, SWSR-202, SWSR-203, SWSR-204, SWSR-205, SWSR-206, SWSR-207";
    }
    verification <'VS-SWQ-06'> vs_swq_06 : VerificationCase {
        doc /* Engagement and brake/gas */
        :>> spec = "WP-W-08 §5";
        :>> level = "VS-SWQ";
        :>> names = "SWSR-301, SWSR-302, SWSR-304, SWSR-305, SWSR-306, SWSR-309, SWSR-311";
    }
    verification <'VS-SWQ-07'> vs_swq_07 : VerificationCase {
        doc /* Driver override and heartbeat mismatch */
        :>> spec = "WP-W-08 §5";
        :>> level = "VS-SWQ";
        :>> names = "SWSR-304, SWSR-304a, SWSR-307";
    }
    verification <'VS-SWQ-08'> vs_swq_08 : VerificationCase {
        doc /* RX timeouts */
        :>> spec = "WP-W-08 §5";
        :>> level = "VS-SWQ";
        :>> names = "SWSR-401, SWSR-401a, SWSR-406";
    }
    verification <'VS-SWQ-09'> vs_swq_09 : VerificationCase {
        doc /* RX plausibility */
        :>> spec = "WP-W-08 §5";
        :>> level = "VS-SWQ";
        :>> names = "SWSR-402, SWSR-403, SWSR-404, SWSR-405";
    }
    verification <'VS-SWQ-10'> vs_swq_10 : VerificationCase {
        doc /* Heartbeat loss, SILENT, siren */
        :>> spec = "WP-W-08 §5";
        :>> level = "VS-SWQ";
        :>> names = "SWSR-407, SWSR-409, SWSR-510, SWSR-516";
    }
    verification <'VS-SWQ-11'> vs_swq_11 : VerificationCase {
        doc /* Command stall */
        :>> spec = "WP-W-08 §5";
        :>> level = "VS-SWQ";
        :>> names = "SWSR-109a, SWSR-408";
    }
    verification <'VS-SWQ-12'> vs_swq_12 : VerificationCase {
        doc /* SPI integrity and bounds on target (also HWSR-401) */
        :>> spec = "WP-W-08 §5";
        :>> level = "VS-SWQ";
        :>> names = "HWSR-401, SWSR-410, SWSR-410a, SWSR-410b, SWSR-411, SWSR-412, SWSR-412a, SWSR-412b, SWSR-413";
    }
    verification <'VS-SWQ-13'> vs_swq_13 : VerificationCase {
        doc /* EPS status monitoring */
        :>> spec = "WP-W-08 §5";
        :>> level = "VS-SWQ";
        :>> names = "SWSR-110";
    }
    verification <'VS-SWQ-14'> vs_swq_14 : VerificationCase {
        doc /* Watchdog and hang */
        :>> spec = "WP-W-08 §5";
        :>> level = "VS-SWQ";
        :>> names = "SWSR-501, SWSR-501b, SWSR-502a";
    }
    verification <'VS-SWQ-15'> vs_swq_15 : VerificationCase {
        doc /* Fault reaction */
        :>> spec = "WP-W-08 §5";
        :>> level = "VS-SWQ";
        :>> names = "SWSR-502, SWSR-502b, SWSR-503a, SWSR-503b, SWSR-504, SWSR-505, SWSR-508, SWSR-509";
    }
    verification <'VS-SWQ-16'> vs_swq_16 : VerificationCase {
        doc /* Start-up tests and image integrity */
        :>> spec = "WP-W-08 §5";
        :>> level = "VS-SWQ";
        :>> names = "SWSR-502c, SWSR-503, SWSR-515";
    }
    verification <'VS-SWQ-17'> vs_swq_17 : VerificationCase {
        doc /* Configuration lock and request gating */
        :>> spec = "WP-W-08 §5";
        :>> level = "VS-SWQ";
        :>> names = "SWSR-511a, SWSR-512, SWSR-512a, SWSR-513, SWSR-514";
    }
    verification <'VS-SWQ-18'> vs_swq_18 : VerificationCase {
        doc /* Bootstub signature */
        :>> spec = "WP-W-08 §5";
        :>> level = "VS-SWQ";
        :>> names = "SWSR-511";
    }
    verification <'VS-SWQ-19'> vs_swq_19 : VerificationCase {
        doc /* Relay readback, orientation, relay latch */
        :>> spec = "WP-W-08 §5";
        :>> level = "VS-SWQ";
        :>> names = "SWSR-506, SWSR-506a, SWSR-506b, SWSR-701, SWSR-701a, SWSR-706, SWSR-710";
    }
    verification <'VS-SWQ-20'> vs_swq_20 : VerificationCase {
        doc /* Envelope reports every revocation cause and fault in the health packet */
        :>> spec = "WP-W-08 §5";
        :>> level = "VS-SWQ";
        :>> names = "SWSR-108a";
    }
    verification <'VS-SWQ-21'> vs_swq_21 : VerificationCase {
        doc /* Forwarding and PCS message rules */
        :>> spec = "WP-W-08 §5";
        :>> level = "VS-SWQ";
        :>> names = "SWSR-704, SWSR-705, SWSR-707";
        objective {
            verify LionDriverRequirements::tsr_707;
        }
    }
    verification <'VS-SWQ-22'> vs_swq_22 : VerificationCase {
        doc /* Relay malfunction detection by traffic */
        :>> spec = "WP-W-08 §5";
        :>> level = "VS-SWQ";
        :>> names = "SWSR-710";
    }
    verification <'VS-SWQ-23'> vs_swq_23 : VerificationCase {
        doc /* Resource usage and timing on target */
        :>> spec = "WP-W-08 §5";
        :>> level = "VS-SWQ";
        :>> names = "SWSR-401a";
    }
    verification <'VS-SWQ-24'> vs_swq_24 : VerificationCase {
        doc /* Endurance replay */
        :>> spec = "WP-W-08 §5";
        :>> level = "VS-SWQ";
        :>> names = "";
    }
    verification <'VS-SWQ-25'> vs_swq_25 : VerificationCase {
        doc /* TX read-back, per-ID TX rate, priority scheme */
        :>> spec = "WP-W-08 §5";
        :>> level = "VS-SWQ";
        :>> names = "SWSR-517, SWSR-518, SWSR-519";
    }
    verification <'VS-SWQ-26'> vs_swq_26 : VerificationCase {
        doc /* EPS-fault siren */
        :>> spec = "WP-W-08 §5";
        :>> level = "VS-SWQ";
        :>> names = "SWSR-516";
        objective {
            verify LionDriverRequirements::tsr_516;
        }
    }
    verification <'VS-UV-01'> vs_uv_01 : VerificationCase {
        doc /* U-SAF-HELP */
        :>> spec = "WP-W-06 §6";
        :>> level = "VS-UV";
        :>> names = "";
    }
    verification <'VS-UV-02'> vs_uv_02 : VerificationCase {
        doc /* U-SAF-LAT, U-SAF-TOY */
        :>> spec = "WP-W-06 §6";
        :>> level = "VS-UV";
        :>> names = "SWSR-101, SWSR-101a, SWSR-102, SWSR-102a";
        objective {
            verify LionDriverRequirements::fsr_01_01;
        }
    }
    verification <'VS-UV-03'> vs_uv_03 : VerificationCase {
        doc /* U-SAF-LAT */
        :>> spec = "WP-W-06 §6";
        :>> level = "VS-UV";
        :>> names = "SWSR-103, SWSR-103a";
        objective {
            verify LionDriverRequirements::fsr_01_02;
        }
    }
    verification <'VS-UV-04'> vs_uv_04 : VerificationCase {
        doc /* U-SAF-LAT, U-SAF-TOY */
        :>> spec = "WP-W-06 §6";
        :>> level = "VS-UV";
        :>> names = "SWSR-104, SWSR-104a";
        objective {
            verify LionDriverRequirements::fsr_01_03;
        }
    }
    verification <'VS-UV-05'> vs_uv_05 : VerificationCase {
        doc /* U-SAF-LAT */
        :>> spec = "WP-W-06 §6";
        :>> level = "VS-UV";
        :>> names = "SWSR-101a, SWSR-105, SWSR-106, SWSR-107, SWSR-108, SWSR-108a";
        objective {
            verify LionDriverRequirements::fsr_01_04;
            verify LionDriverRequirements::fsr_01_12;
        }
    }
    verification <'VS-UV-06'> vs_uv_06 : VerificationCase {
        doc /* U-SAF-CORE, U-SAF-TOY */
        :>> spec = "WP-W-06 §6";
        :>> level = "VS-UV";
        :>> names = "SWSR-301, SWSR-302, SWSR-311";
        objective {
            verify LionDriverRequirements::fsr_01_05;
            verify LionDriverRequirements::fsr_05_01;
            verify LionDriverRequirements::fsr_05_02;
        }
    }
    verification <'VS-UV-07'> vs_uv_07 : VerificationCase {
        doc /* U-SAF-LONG, U-SAF-TOY */
        :>> spec = "WP-W-06 §6";
        :>> level = "VS-UV";
        :>> names = "SWSR-201, SWSR-201a, SWSR-202, SWSR-203, SWSR-305";
        objective {
            verify LionDriverRequirements::fsr_03_01;
        }
    }
    verification <'VS-UV-08'> vs_uv_08 : VerificationCase {
        doc /* U-SAF-LONG */
        :>> spec = "WP-W-06 §6";
        :>> level = "VS-UV";
        :>> names = "SWSR-204, SWSR-205";
        objective {
            verify LionDriverRequirements::fsr_03_03;
            verify LionDriverRequirements::fsr_04_02;
        }
    }
    verification <'VS-UV-09'> vs_uv_09 : VerificationCase {
        doc /* U-SAF-CORE, U-SAF-TOY */
        :>> spec = "WP-W-06 §6";
        :>> level = "VS-UV";
        :>> names = "SWSR-108a, SWSR-402, SWSR-403, SWSR-404, SWSR-405, SWSR-406";
        objective {
            verify LionDriverRequirements::fsr_01_06;
        }
    }
    verification <'VS-UV-10'> vs_uv_10 : VerificationCase {
        doc /* U-SAF-CORE */
        :>> spec = "WP-W-06 §6";
        :>> level = "VS-UV";
        :>> names = "SWSR-306, SWSR-401, SWSR-401a";
        objective {
            verify LionDriverRequirements::fsr_01_06;
            verify LionDriverRequirements::tsr_401;
        }
    }
    verification <'VS-UV-11'> vs_uv_11 : VerificationCase {
        doc /* U-SAF-CORE */
        :>> spec = "WP-W-06 §6";
        :>> level = "VS-UV";
        :>> names = "SWSR-710";
        objective {
            verify LionDriverRequirements::fsr_01_11;
        }
    }
    verification <'VS-UV-12'> vs_uv_12 : VerificationCase {
        doc /* U-SAF-TOY (init) */
        :>> spec = "WP-W-06 §6";
        :>> level = "VS-UV";
        :>> names = "SWSR-104a, SWSR-512, SWSR-512a";
        objective {
            verify LionDriverRequirements::fsr_01_10;
        }
    }
    verification <'VS-UV-13'> vs_uv_13 : VerificationCase {
        doc /* U-PND-COMMS */
        :>> spec = "WP-W-06 §6";
        :>> level = "VS-UV";
        :>> names = "SWSR-104a, SWSR-512, SWSR-512a, SWSR-513, SWSR-514";
        objective {
            verify LionDriverRequirements::fsr_01_10;
        }
    }
    verification <'VS-UV-14'> vs_uv_14 : VerificationCase {
        doc /* U-PND-MAIN */
        :>> spec = "WP-W-06 §6";
        :>> level = "VS-UV";
        :>> names = "SWSR-307, SWSR-401a, SWSR-407, SWSR-409, SWSR-510, SWSR-516, SWSR-516a, SWSR-516b";
        objective {
            verify LionDriverRequirements::fsr_01_07;
            verify LionDriverRequirements::fsr_02_05;
        }
    }
    verification <'VS-UV-15'> vs_uv_15 : VerificationCase {
        doc /* U-PND-SPI, U-PND-COMMS, U-PND-FDCAN */
        :>> spec = "WP-W-06 §6";
        :>> level = "VS-UV";
        :>> names = "SWSR-410, SWSR-410a, SWSR-410b, SWSR-411, SWSR-412, SWSR-412a, SWSR-412b, SWSR-413";
        objective {
            verify LionDriverRequirements::fsr_01_08;
        }
    }
    verification <'VS-UV-16'> vs_uv_16 : VerificationCase {
        doc /* U-PND-FLT, U-PND-MAIN */
        :>> spec = "WP-W-06 §6";
        :>> level = "VS-UV";
        :>> names = "SWSR-501, SWSR-501b, SWSR-502, SWSR-502a, SWSR-502b, SWSR-502c, SWSR-503, SWSR-503a, SWSR-503b, SWSR-503c";
        objective {
            verify LionDriverRequirements::fsr_01_09;
        }
    }
    verification <'VS-UV-17'> vs_uv_17 : VerificationCase {
        doc /* U-SAF-TOY, U-SAF-LAT */
        :>> spec = "WP-W-06 §6";
        :>> level = "VS-UV";
        :>> names = "SWSR-110, SWSR-304, SWSR-304a, SWSR-516";
        objective {
            verify LionDriverRequirements::fsr_02_01;
            verify LionDriverRequirements::fsr_05_03;
        }
    }
    verification <'VS-UV-18'> vs_uv_18 : VerificationCase {
        doc /* U-SAF-CORE, U-SAF-TOY */
        :>> spec = "WP-W-06 §6";
        :>> level = "VS-UV";
        :>> names = "SWSR-207, SWSR-704, SWSR-705";
        objective {
            verify LionDriverRequirements::fsr_07_01;
        }
    }
    verification <'VS-UV-19'> vs_uv_19 : VerificationCase {
        doc /* all U-SAF-* */
        :>> spec = "WP-W-06 §6";
        :>> level = "VS-UV";
        :>> names = "SWSR-514";
    }
    verification <'VS-UV-20'> vs_uv_20 : VerificationCase {
        doc /* all E-03 units */
        :>> spec = "WP-W-06 §6";
        :>> level = "VS-UV";
        :>> names = "";
    }
    verification <'VS-UV-21'> vs_uv_21 : VerificationCase {
        doc /* all E-03 units */
        :>> spec = "WP-W-06 §6";
        :>> level = "VS-UV";
        :>> names = "SWSR-501, SWSR-501b";
    }
    verification <'VS-UV-22'> vs_uv_22 : VerificationCase {
        doc /* U-PND-BOOT */
        :>> spec = "WP-W-06 §6";
        :>> level = "VS-UV";
        :>> names = "SWSR-511, SWSR-511a";
    }
    verification <'VS-UV-23'> vs_uv_23 : VerificationCase {
        doc /* U-SAF-CORE, U-SAF-TOY */
        :>> spec = "WP-W-06 §6";
        :>> level = "VS-UV";
        :>> names = "SWSR-518";
        objective {
            verify LionDriverRequirements::fsr_01_08;
            verify LionDriverRequirements::fsr_01_12;
        }
    }
    verification <'VS-VAL-01'> vs_val_01 : VerificationCase {
        doc /* EPS LKA torque authority (AOU-01) */
        :>> spec = "WP-V-01 §5.1";
        :>> level = "VS-VAL";
        :>> names = "AOU-01";
        objective {
            verify LionDriverRequirements::fsr_01_13;
        }
    }
    verification <'VS-VAL-02'> vs_val_02 : VerificationCase {
        doc /* EPS behaviour when LKA messages stop (AOU-01) */
        :>> spec = "WP-V-01 §5.1";
        :>> level = "VS-VAL";
        :>> names = "AOU-01";
        objective {
            verify LionDriverRequirements::fsr_01_13;
        }
    }
    verification <'VS-VAL-03'> vs_val_03 : VerificationCase {
        doc /* Driver override force (AOU-02) */
        :>> spec = "WP-V-01 §5.1";
        :>> level = "VS-VAL";
        :>> names = "AOU-02";
        objective {
            verify LionDriverRequirements::fsr_05_03;
        }
    }
    verification <'VS-VAL-04'> vs_val_04 : VerificationCase {
        doc /* Brake override (AOU-03) */
        :>> spec = "WP-V-01 §5.1";
        :>> level = "VS-VAL";
        :>> names = "AOU-03";
        objective {
            verify LionDriverRequirements::sg_05;
            verify LionDriverRequirements::fsr_05_07;
        }
    }
    verification <'VS-VAL-05'> vs_val_05 : VerificationCase {
        doc /* PCM ACC envelope and cancel (AOU-05) */
        :>> spec = "WP-V-01 §5.1";
        :>> level = "VS-VAL";
        :>> names = "AOU-05, HE-03.1, HE-04.1";
        objective {
            verify LionDriverRequirements::fsr_03_06;
            verify LionDriverRequirements::fsr_04_03;
        }
    }
    verification <'VS-VAL-06'> vs_val_06 : VerificationCase {
        doc /* Stock PCS preservation (AOU-04) */
        :>> spec = "WP-V-01 §5.1";
        :>> level = "VS-VAL";
        :>> names = "AOU-04";
        objective {
            verify LionDriverRequirements::sg_07;
            verify LionDriverRequirements::fsr_07_04;
        }
    }
    verification <'VS-VAL-07'> vs_val_07 : VerificationCase {
        doc /* VSC/ABS status visibility (AOU-10) */
        :>> spec = "WP-V-01 §5.1";
        :>> level = "VS-VAL";
        :>> names = "AOU-10, H-01, H-04, HE-04.2";
    }
    verification <'VS-VAL-08'> vs_val_08 : VerificationCase {
        doc /* PCM ACC response onset (planning-to-actuation time) */
        :>> spec = "WP-V-01 §5.1";
        :>> level = "VS-VAL";
        :>> names = "AIR-03, AIR-04";
    }
    verification <'VS-VAL-10'> vs_val_10 : VerificationCase {
        doc /* Worst-case lateral disturbance inside the envelope */
        :>> spec = "WP-V-01 §5.2";
        :>> level = "VS-VAL";
        :>> names = "HE-01.1, HE-01.2, HE-01.3, HE-01.4, HE-01.5, HE-01.6";
        objective {
            verify LionDriverRequirements::sg_01;
        }
    }
    verification <'VS-VAL-11'> vs_val_11 : VerificationCase {
        doc /* Lateral deviation vs time at envelope limits (no driver reaction) */
        :>> spec = "WP-V-01 §5.2";
        :>> level = "VS-VAL";
        :>> names = "";
        objective {
            verify LionDriverRequirements::sg_01;
            verify LionDriverRequirements::fsr_01_01;
        }
    }
    verification <'VS-VAL-12'> vs_val_12 : VerificationCase {
        doc /* Unexpected loss of lateral control in a curve with take-over warning */
        :>> spec = "WP-V-01 §5.2";
        :>> level = "VS-VAL";
        :>> names = "HE-02.1";
        objective {
            verify LionDriverRequirements::sg_02;
        }
    }
    verification <'VS-VAL-13'> vs_val_13 : VerificationCase {
        doc /* Unexpected acceleration while following */
        :>> spec = "WP-V-01 §5.2";
        :>> level = "VS-VAL";
        :>> names = "";
        objective {
            verify LionDriverRequirements::sg_03;
        }
    }
    verification <'VS-VAL-14'> vs_val_14 : VerificationCase {
        doc /* Unexpected deceleration step */
        :>> spec = "WP-V-01 §5.2";
        :>> level = "VS-VAL";
        :>> names = "HE-04.1";
        objective {
            verify LionDriverRequirements::sg_04;
        }
    }
    verification <'VS-VAL-15'> vs_val_15 : VerificationCase {
        doc /* Release on driver input */
        :>> spec = "WP-V-01 §5.2";
        :>> level = "VS-VAL";
        :>> names = "AOU-02";
        objective {
            verify LionDriverRequirements::sg_05;
            verify LionDriverRequirements::fsr_05_01;
        }
    }
    verification <'VS-VAL-16'> vs_val_16 : VerificationCase {
        doc /* Loss of longitudinal deceleration with warning */
        :>> spec = "WP-V-01 §5.2";
        :>> level = "VS-VAL";
        :>> names = "";
        objective {
            verify LionDriverRequirements::sg_06;
            verify LionDriverRequirements::fsr_06_02;
        }
    }
    verification <'VS-VAL-17'> vs_val_17 : VerificationCase {
        doc /* DM-supported controllability */
        :>> spec = "WP-V-01 §5.2";
        :>> level = "VS-VAL";
        :>> names = "SH-12";
        objective {
            verify LionDriverRequirements::fsr_02_06;
            verify LionDriverRequirements::tsr_634;
        }
    }
    verification <'VS-VAL-18'> vs_val_18 : VerificationCase {
        doc /* Alert perceptibility */
        :>> spec = "WP-V-01 §5.2";
        :>> level = "VS-VAL";
        :>> names = "";
        objective {
            verify LionDriverRequirements::sg_02;
            verify LionDriverRequirements::sg_06;
        }
    }
    verification <'VS-VAL-20'> vs_val_20 : VerificationCase {
        doc /* Heartbeat supervision */
        :>> spec = "WP-V-01 §5.3";
        :>> level = "VS-VAL";
        :>> names = "";
    }
    verification <'VS-VAL-21'> vs_val_21 : VerificationCase {
        doc /* RX checks */
        :>> spec = "WP-V-01 §5.3";
        :>> level = "VS-VAL";
        :>> names = "";
    }
    verification <'VS-VAL-22'> vs_val_22 : VerificationCase {
        doc /* Torque and accel limits */
        :>> spec = "WP-V-01 §5.3";
        :>> level = "VS-VAL";
        :>> names = "";
    }
    verification <'VS-VAL-23'> vs_val_23 : VerificationCase {
        doc /* Engagement gating */
        :>> spec = "WP-V-01 §5.3";
        :>> level = "VS-VAL";
        :>> names = "";
    }
    verification <'VS-VAL-24'> vs_val_24 : VerificationCase {
        doc /* Relay malfunction */
        :>> spec = "WP-V-01 §5.3";
        :>> level = "VS-VAL";
        :>> names = "";
    }
    verification <'VS-VAL-25'> vs_val_25 : VerificationCase {
        doc /* Safety-mode integrity */
        :>> spec = "WP-V-01 §5.3";
        :>> level = "VS-VAL";
        :>> names = "";
        objective {
            verify LionDriverRequirements::tsr_512;
        }
    }
    verification <'VS-VAL-26'> vs_val_26 : VerificationCase {
        doc /* Host fault reactions */
        :>> spec = "WP-V-01 §5.3";
        :>> level = "VS-VAL";
        :>> names = "";
        objective {
            verify LionDriverRequirements::sg_02;
        }
    }
    verification <'VS-VAL-30'> vs_val_30 : VerificationCase {
        doc /* Toyota EPS LKA torque limiting and fault handling */
        :>> spec = "WP-V-01 §5.4";
        :>> level = "VS-VAL";
        :>> names = "";
    }
    verification <'VS-VAL-31'> vs_val_31 : VerificationCase {
        doc /* PCM brake override and ACC envelope */
        :>> spec = "WP-V-01 §5.4";
        :>> level = "VS-VAL";
        :>> names = "";
    }
    verification <'VS-VAL-32'> vs_val_32 : VerificationCase {
        doc /* Stock PCS/AEB */
        :>> spec = "WP-V-01 §5.4";
        :>> level = "VS-VAL";
        :>> names = "";
    }
    verification <'VS-VAL-40'> vs_val_40 : VerificationCase {
        doc /* Alert and HMI behaviour in the ODD */
        :>> spec = "WP-V-01 §5.5";
        :>> level = "VS-VAL";
        :>> names = "";
    }
    verification <'VS-VAL-41'> vs_val_41 : VerificationCase {
        doc /* DM nuisance and effectiveness */
        :>> spec = "WP-V-01 §5.5";
        :>> level = "VS-VAL";
        :>> names = "AIR-08";
    }
    verification <'VS-VAL-42'> vs_val_42 : VerificationCase {
        doc /* Envelope limit hits */
        :>> spec = "WP-V-01 §5.5";
        :>> level = "VS-VAL";
        :>> names = "";
    }
    verification <'VS-VAL-43'> vs_val_43 : VerificationCase {
        doc /* Environmental conditions */
        :>> spec = "WP-V-01 §5.5";
        :>> level = "VS-VAL";
        :>> names = "";
    }
}
